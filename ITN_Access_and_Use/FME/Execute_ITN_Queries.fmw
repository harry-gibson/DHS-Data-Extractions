FME workspace Execute_ITN_Queries.fmw

Parameters:
- DestDataset_CSV = \\map-fs1.ndph.ox.ac.uk\map_data\DHS_Automation\Processing\ITN_Usage_MAP_Extract\2018_07_12_Run\output   # Destination CSV (Comma Separated Value) Folder
- CLUSTER_TEMPLATE_SQL = $(FME_MF_DIR_ENCODED)ITN_By_Cluster_Generic_Template_RECH7.sql   # Cluster SQL Template
- HH_TEMPLATE_SQL = $(FME_MF_DIR)ITN_By_HH_Generic_Template_RECH7.sql   # Household SQL Template
- SourceDataset_CSV2 = \\map-fs1.ndph.ox.ac.uk\map_data\DHS_Automation\Processing\ITN_Usage_MAP_Extract\2018_07_12_Run\config\output.csv   # Source CSV (Comma Separated Value) File(s)

Readers:
- CSV2_1: CSV2 from $(SourceDataset_CSV2)

Writers:
- CSV_2: CSV to $(DestDataset_CSV)
- CSV_3: CSV to $(DestDataset_CSV)

CSV (reader CSV2_1)
    attributes: itemtype string, recordname string, recordtypevalue string, recordlabel string, name string, label string, start string, len string, fmetype string, surveyid string
    -> AttributeRenamer
AttributeRenamer
    ATTR_TABLE = RENAME_SET_DEFAULT surveyid > SurveyID
    -> Tester
Tester
    TEST_CLAUSE = TEST @Value(recordname) = RECH7
    TEST_MODE = Automatic
    BOOL_OP = OR
    TEST_DESCRIPTION = ""
    PASSED -> AttributeKeeper_2
AttributeKeeper_2
    KEEP_ATTRS = SurveyID
    -> AttributeFileReader
    -> AttributeFileReader_2
AttributeFileReader
    CHAR_ENCODING = fme-binary
    DEST_ATTR = _SQL
    FILE_NAME = $(CLUSTER_TEMPLATE_SQL)
    -> StringReplacer
StringReplacer
    REPLACE_TEXT = @Value(SurveyID)
    FIND_TEXT = {SURVEYID}
    REGEXP = NO
    SRC_ATTRS = _SQL
    CASE = NO
    NO_MATCH = _FME_NO_OP_
    -> SQLExecutor [INITIATOR] [off]
    -> Cluster_Qry
SQLExecutor
    SQL_STATEMENT = @Value(_SQL)
    POSTGRES_QUERY_FEATURE_TYPES_FOR_MERGE_FILTERS = Yes
    COMBINE_GEOM = Initiator Geometry Only
    POSTGRES_SCHEMAS_FOR_TABLE_LISTING = dhs_data_locations dhs_data_tables
    POSTGRES_NAMED_CONNECTION = DHS Data Readonly
    FORMAT = POSTGRES
    COMBINE_ATTRS = Keep Result Attributes if Conflict
    DATASET = DHS Data Readonly
    EXPOSED_ATTRIBUTE_LIST = clusterid,latitude,longitude,location_src,n_pop_u5,n_u5_under_itn,n_preg_tot,n_preg_under_itn,n_defacto_pop,n_slept_under_itn,n_hh_tot,n_hh_in_net_tbl_tot,mean_hh_size,n_itn,n_hh_with_itn,n_hh_with_enough_itn,n_occ_hh_with_enough_itn,itn_usable_capacity,n_itn_used,n_conv_itn,n_llin,n_llin_1yr,n_llin_1_2yr,n_llin_2_3yr,n_llin_gt3yr
    RESULT -> StatisticsCalculator
    RESULT -> AttributeCreator
AttributeCreator
    ATTR_TABLE = SET_TO _outname = Svy_@Value(SurveyID)_ITN_Cluster_Res
    -> File1 (writer CSV_3)
File1 (writer CSV_3)
    attributes: SurveyID number(4,0), clusterid auto, latitude auto, longitude auto, location_src auto, n_pop_u5 auto, n_u5_under_itn auto, n_preg_tot auto, n_preg_under_itn auto, n_defacto_pop auto, n_slept_under_itn auto, n_hh_tot auto, n_hh_in_net_tbl_tot auto, mean_hh_size auto, n_itn auto, n_hh_with_itn auto, n_hh_with_enough_itn auto, n_occ_hh_with_enough_itn auto, itn_usable_capacity auto, n_itn_used auto, n_conv_itn auto, n_llin auto, n_llin_1yr auto, n_llin_1_2yr auto, n_llin_2_3yr auto, n_llin_gt3yr auto
StatisticsCalculator
    STATS_ATTRS = n_u5_under_itn n_llin n_itn n_preg_under_itn n_conv_itn
    GROUP_BY = SurveyID
    PREPEND_ATTR_NAME_CHOICE = For multiple results only
    COMPUTE_HISTOGRAM = NO
    MAX_ATTR = _max
    SUMMARY -> ClusterLevel_Summary
    SUMMARY -> Cluster_Res_Summary (writer CSV_2)
ClusterLevel_Summary: Inspector
Cluster_Res_Summary (writer CSV_2)
    attributes: SurveyID auto, n_u5_under_itn._max auto, n_llin._max auto, n_itn._max auto, n_preg_under_itn._max auto, n_conv_itn._max auto
Cluster_Qry: Inspector [off]
AttributeFileReader_2
    CHAR_ENCODING = fme-system
    DEST_ATTR = _SQL
    FILE_NAME = $(HH_TEMPLATE_SQL)
    -> StringReplacer_2
StringReplacer_2
    REPLACE_TEXT = @Value(SurveyID)
    FIND_TEXT = {SURVEYID}
    REGEXP = NO
    SRC_ATTRS = _SQL
    CASE = NO
    NO_MATCH = _FME_NO_OP_
    -> SQLExecutor_2 [INITIATOR]
    -> HH_Qry
SQLExecutor_2
    SQL_STATEMENT = @Value(_SQL)
    POSTGRES_QUERY_FEATURE_TYPES_FOR_MERGE_FILTERS = Yes
    COMBINE_GEOM = Initiator Geometry Only
    POSTGRES_SCHEMAS_FOR_TABLE_LISTING = dhs_data_locations dhs_data_tables
    POSTGRES_NAMED_CONNECTION = DHS Data Readonly
    FORMAT = POSTGRES
    COMBINE_ATTRS = Keep Result Attributes if Conflict
    DATASET = DHS Data Readonly
    EXPOSED_ATTRIBUTE_LIST = clusterid,hh_has_enough_itn,hh_has_entry_in_net_tbl,hh_has_itn,hh_sample_wt,hh_size,hhid,interview_month,interview_year,itn_theoretical_capacity,latitude,location_src,longitude,n_conv_itn,n_defacto_pop,n_itn,n_itn_used,n_llin,n_llin_1_2yr,n_llin_1yr,n_llin_2_3yr,n_llin_gt3yr,n_pop_u5,n_preg_tot,n_preg_under_itn,n_slept_under_itn,n_u5_under_itn,occ_hh_has_enough_itn
    RESULT -> AttributeCreator_2
    RESULT -> StatisticsCalculator_2
AttributeCreator_2
    ATTR_TABLE = SET_TO _outname = Svy_@Value(SurveyID)_ITN_HH_Res
    -> File1 (writer CSV_2)
File1 (writer CSV_2)
    attributes: SurveyID number(4,0), clusterid auto, hhid auto, latitude auto, longitude auto, location_src auto, interview_year auto, interview_month auto, hh_sample_wt auto, n_pop_u5 auto, n_u5_under_itn auto, n_preg_tot auto, n_preg_under_itn auto, n_defacto_pop auto, n_slept_under_itn auto, hh_has_entry_in_net_tbl auto, hh_size auto, n_itn auto, hh_has_itn auto, hh_has_enough_itn auto, occ_hh_has_enough_itn auto, itn_theoretical_capacity auto, n_itn_used auto, n_conv_itn auto, n_llin auto, n_llin_1_2yr auto, n_llin_1yr auto, n_llin_2_3yr auto, n_llin_gt3yr auto
StatisticsCalculator_2
    STATS_ATTRS = n_u5_under_itn n_llin n_itn n_preg_under_itn n_conv_itn
    GROUP_BY = SurveyID
    PREPEND_ATTR_NAME_CHOICE = For multiple results only
    COMPUTE_HISTOGRAM = NO
    MAX_ATTR = _max
    SUMMARY -> HH_Res_Summary (writer CSV_2)
    SUMMARY -> HHLevel_Summary
HH_Res_Summary (writer CSV_2)
    attributes: SurveyID auto, n_u5_under_itn._max auto, n_llin._max auto, n_itn._max auto, n_preg_under_itn._max auto, n_conv_itn._max auto
HHLevel_Summary: Inspector
HH_Qry: Inspector [off]
