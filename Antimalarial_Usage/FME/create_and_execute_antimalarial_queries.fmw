FME workspace create_and_execute_antimalarial_queries.fmw

Parameters:
- OutputFolder = \\map-fs1.ndph.ox.ac.uk\map_data\DHS_Automation\Processing\Antimalarial_Usage_V2\output_20190704   # Output Folder
- SourceDataset_CSV2 = Z:\DHS_Automation\Processing\Antimalarial_Usage_V2\Info\antimalarial_usage_20190704.csv   # Source CSV (Comma Separated Value) File(s)
- SourceDataset_CSV2_4 = Z:\DHS_Automation\Processing\Antimalarial_Usage_V2\info\output_schema_20180903.csv   # Source CSV (Comma Separated Value) File(s)
- DHS_Surveys_API_URL = http://api.dhsprogram.com/rest/dhs/surveys?f=csv   # API URL for DHS surveys in CSV format

Readers:
- CSV2_1: CSV2 from $(DHS_Surveys_API_URL)
- CSV2_2: CSV2 from $(SourceDataset_CSV2)
- CSV2_3: CSV2 from $(SourceDataset_CSV2_4)

Writers:
- CSV2_4: CSV2 to $(OutputFolder)

CSV (reader CSV2_2)
    attributes: surveyid string, recordname string, name string, label string, treated_act string, treated_act_al string, treated_act_asaq string, treated_act_asmq string, treated_dhasp string, treated_mono_as string, treated_mono_am string, treated_mono_arte string, treated_aq string, treated_cq string, treated_qn string, treated_pq string, treated_mq string, treated_sp string, treated_sp_cq string, treated_sp_aq string, treated_other_anti string, treated_any_anti string, treated_antipyretic string, treated_antibiotic string, treated_other_drug string, treated_traditional string, treated_dontknow string, ok_to_run string, why_not string, added_hg string,
      in_use string, used_last_time string, not_treated string
    -> Tester_9
Tester_9
    BOOL_OP = AND
    TEST_CLAUSE:
      TEST @Value(ok_to_run) IN y,c
      TEST @Value(in_use) = 1
    TEST_MODE = TEST
    PASSED -> AttributeCreator
Note: Create a value in:out map for each input column mentioned in the mapping sheet / For each output "type" column, every input column that can contribute to it will go into a "CASE WHEN x OR y OR z" clause in the form H32A::Integer=1. However tables REC95 and REC94 are stored with all their data in a jsonb column, so we need to extract the relevant fields. Format these clauses depending on the source table. / Specify how to join the input table / The different input tables have different column names to join them onto REC21. Build the appropriate join clause that will be used
AttributeCreator
    ATTR_TABLE:
      SET_TO _qualColumnValueSelector = FME_CONDITIONAL:DEFAULT_VALUE'@LowerCase(@Value(recordname)).@LowerCase(@Value(name))::Integer=1'BOOL_OP;OR;COMPOSITE_TEST;<Unused>;TEST @Value(recordname) IN REC94,REC95'@LowerCase(@Value(recordname)).data->>'@LowerCase(@Value(name))'='1''FME_NUM_CONDITIONS2___
      SET_TO _amTableJoinCol = FME_CONDITIONAL:DEFAULT_VALUE'XXXX'BOOL_OP;OR;COMPOSITE_TEST;<Unused>;TEST @Value(recordname) = REC43'HIDX'BOOL_OP;OR;COMPOSITE_TEST;<Unused>;TEST @Value(recordname) = REC4A'HIDXA'BOOL_OP;OR;COMPOSITE_TEST;<Unused>;TEST @Value(recordname) = REC41'MIDX'BOOL_OP;OR;COMPOSITE_TEST;<Unused>;TEST @Value(recordname) = REC95'IDX95'BOOL_OP;OR;COMPOSITE_TEST;<Unused>;TEST @Value(recordname) = REC94'IDX94'BOOL_OP;OR;COMPOSITE_TEST;<Unused>;TEST @Value(recordname) = RECML'IDXML'BOOL_OP;OR;COMPOSITE_TEST;<Unused>;TEST @Value(recordname) = REC98'IDX98'FME_NUM_CONDITIONS8___
      SET_TO _qualTableJoinClause = dhs_data_tables."@Value(recordname)" @LowerCase(@Value(recordname))
        ON
        r21.surveyid = @LowerCase(@Value(recordname)).surveyid
        AND
        r21.caseid = @LowerCase(@Value(recordname)).caseid
        AND
        r21.BIDX = @LowerCase(@Value(recordname)).@Value(_amTableJoinCol)
    -> BulkAttributeRenamer
Note: Convert to key/value pair format, keeping only the ones from columns relating to a mapped output column
BulkAttributeRenamer
    ATTRCHOICE = Selected Attributes
    ATTRLIST = treated_traditional treated_other_anti treated_any_anti treated_cq treated_dontknow treated_sp_aq not_treated treated_act treated_act_asaq treated_aq treated_pq treated_antipyretic treated_dhasp treated_sp_cq treated_antibiotic treated_sp treated_mq treated_qn treated_act_asmq treated_other_drug treated_mono_am treated_mono_as treated_act_al treated_mono_arte
    MODE_CHOICE = RENAME
    PATTERN_ACTION_DISP = ADDPREFIX
    REPLACE_STR = q_
    -> AttributeExploder
AttributeExploder
    ATTR_NAME_LABEL = _attr_name
    ATTR_VALUE_LABEL = _attr_value
    EXPLODING_TYPE = Features
    KEEP_ATTRIBUTES = Yes
    KEEP_GEOMETRY = No
    -> Tester_8
Note: Keep the question/answer pairs flagged by Donal as 1
Tester_8
    BOOL_OP = AND
    TEST_CLAUSE:
      TEST @Value(_attr_name) BEGINS_WITH q_
      TEST @Value(_attr_value) = 1
    TEST_MODE = TEST
    PASSED -> AttributeKeeper_5
AttributeKeeper_5
    KEEP_ATTRS = surveyid,_qualColumnValueSelector,_attr_value,recordname,_amTableJoinCol,_attr_name,_qualTableJoinClause,name,label
    -> ListBuilder
    -> ListBuilder_2
ListBuilder_3
    GROUP_BY = surveyid
    LIST_ATTRS_TO_INCLUDE = _outputColumnName _outputColumnSelectClause
    LIST_NAME = _list
    -> ListConcatenator_5
ListConcatenator_5
    DROP_EMPTY_PARTS = No
    LIST_ATTR = _list{}._outputColumnSelectClause
    SEP = ,
    VAL_ATTR = _OutputColumnSelectors
    -> AttributeRemover_3
AttributeRemover_3
    LIST_ATTRS = _list{}
    -> FeatureMerger_9 [SUPPLIER]
    -> SelectorsBySurvey
Note: Merge to one feature per survey, containing the output column selectors and the table join clauses
FeatureMerger_9
    ATTR_ACCUM_MODE = Merge Supplier
    ATTR_CONFLICT_RES = Use Requestor
    CLEANING_TOLERANCE = None
    IGNORE_NULLS = No
    JOIN_KEYS = @Value(surveyid) @Value(surveyid) AUTO
    MERGE_TYPE = Attributes Only
    PROCESS_DUPS = No
    REJECT_NULL_MISSING_KEYS = No
    SUPPLIERS_FIRST = No
    MERGED -> AttributeManager_13
Note: Using the collated information build the overall SQL query to select the results at a child level for one survey
AttributeManager_13
    ATTR_TABLE:
      SET_TO _outSQL = SELECT
        r21.bidx as child_num
        , r01.caseid as woman_id
        , r01.v001 as clusterid
        , r01.v024 as region
        , r01.v005 as wt
        , clust.latnum as latitude
        , clust.longnum as longitude
        , h0.hv025 as urban_rural
        , r11.v190 as wealth_quint
        , r01.v005::Float / 1000000 as sample_wt
        , r21.b5 as child_is_alive
        , r21.b8 as child_age
        , @Value(_OutputColumnSelectors)
        FROM
        -- the child level master table
        dhs_data_tables."REC21" r21
        INNER JOIN
            -- the woman level table, can safely inner-join
            dhs_data_tables."REC01" r01
        ON r21.surveyid::INTEGER = r01.surveyid::INTEGER AND r21.caseid = r01.caseid
        LEFT OUTER JOIN
            -- the woman extended data table, use outer join in case data don't exist
            dhs_data_tables."REC11" r11
        ON r01.surveyid::INTEGER = r11.surveyid::INTEGER AND r01.caseid = r11.caseid
        LEFT OUTER JOIN
            -- the household-level table, should be inner join but use outer in case the substring operation messes up
            dhs_data_tables."RECH0" h0
            -- dirty, but this is how it works
        ON r01.surveyid = h0.surveyid AND LEFT(r01.caseid, -3) = h0.hhid
        LEFT OUTER JOIN
            -- the cluster data, outer join as not all surveys contain this
            dhs_data_locations.dhs_cluster_locs clust
        ON r01.surveyid::Integer = clust.surveyid AND r01.v001::Integer = clust.dhsclust
        LEFT OUTER JOIN
        @Value(_TableJoiners)
        WHERE r21.surveyid::Integer=@Value(surveyid) AND r21.b5::Integer=1 AND r21.b8::Integer<=5
        ORDER BY r21.surveyid::Integer, r01.v024::Integer, r01.v001::Integer, r01.caseid, r21.bidx::Integer
    -> Selectors_Output
    -> Junction
Note: Send forward to execute the SQL
Junction
    -> Junction_2
Selectors_Output: Inspector
SelectorsBySurvey: Inspector

Bookmark: Build the SQL to join each AM table, for each survey
ListBuilder_2
    GROUP_BY = surveyid
    LIST_ATTRS_TO_INCLUDE = _amTableJoinCol _qualTableJoinClause
    LIST_NAME = _outCols
    -> ListDuplicateRemover_3
ListDuplicateRemover_3
    SRC_LIST = _outCols{}._qualTableJoinClause
    -> ListConcatenator_4
ListConcatenator_4
    DROP_EMPTY_PARTS = Yes
    LIST_ATTR = _outCols{}._qualTableJoinClause
    SEP = " LEFT OUTER JOIN "
    VAL_ATTR = _TableJoiners
    -> AttributeManager_12
AttributeManager_12
    ATTR_TABLE:
      REMOVE _outCols{}._amTableJoinCol
      REMOVE _outCols{}._qualTableJoinClause
    -> JoinersOutput
    -> FeatureMerger_9 [REQUESTOR]
JoinersOutput: Inspector

Bookmark: Concatenate the inputs for each output column within each survey
ListBuilder
    GROUP_BY = surveyid _attr_name
    LIST_ATTRS_TO_INCLUDE = _qualColumnValueSelector name _qualTableJoinClause
    LIST_NAME = _list
    -> ListConcatenator_3
ListConcatenator_3
    DROP_EMPTY_PARTS = No
    LIST_ATTR = _list{}._qualColumnValueSelector
    SEP = " OR "
    VAL_ATTR = _SvyTableColumnsClause
    -> AttributeManager_10
AttributeManager_10
    ATTR_TABLE:
      SET_TO _outputColumnName = @Substring(@Value(_attr_name),2,-1)
      REMOVE _attr_name
      REMOVE _list{}.name
      SET_TO _outputColumnSelectClause = CASE WHEN (@Value(_SvyTableColumnsClause)) THEN 1 ELSE 0 END AS @Value(_outputColumnName)

      REMOVE _SvyTableColumnsClause
      REMOVE _list{}._qualColumnValueSelector
    -> SelectorsBySvyAndCol
    -> ListBuilder_3
SelectorsBySvyAndCol: Inspector

Bookmark: Build and run the queries
Note: Features with the SQL per survey
Junction_2
    -> FeatureMerger_10 [REQUESTOR]
CSV (reader CSV2_1)
    attributes: SurveyId string, DHS_CountryCode string, SurveyYear string, SurveyType string, SurveyStatus string, CountryName string, SurveyYearLabel string, SurveyNum string, IndicatorData string, RegionName string, SubregionName string, PublicationDate string, ReleaseDate string, SurveyCharacteristicIds string, Footnotes string, FieldworkStart string, FieldworkEnd string, ImplementingOrg string, NumberOfSamplePoints string, NumberofHouseholds string, UniverseOfWomen string, NumberOfWomen string, MinAgeWomen string, MaxAgeWomen string, UniverseOfMen string, NumberOfMen string, MinAgeMen string, MaxAgeMen string, NumberOfFacilities string
    -> AttributeManager_16
Note: Attach other info about the survey: year, country name, text-format survey id. Read from the DHS API.
AttributeManager_16
    ATTR_TABLE:
      RENAME_SET_VALUE SurveyId > SurveyName
      RENAME_SET_VALUE SurveyNum > SurveyId
    -> FeatureMerger_10 [SUPPLIER]
AttributeManager_15
    ATTR_TABLE:
      RENAME_SET_VALUE surveyid > SurveyId
      SET_TO _OutFN = AM_Usage_ByChild_@Value(SurveyId)_@Value(SurveyName)
      SET_TO _OutFN_Single = AM_Usage_ByChild_ALL
    -> d (writer CSV2_4)
d (writer CSV2_4)
    attributes: SurveyId string, region string, clusterid string, woman_id string, child_num string, latitude string, longitude string, urban_rural string, wealth_quint string, sample_wt string, treated_act string, treated_act_al string, treated_act_asaq string, treated_act_asmq string, treated_dhasp string, treated_mono_as string, treated_mono_am string, treated_mono_arte string, treated_aq string, treated_cq string, treated_qn string, treated_pq string, treated_mq string, treated_sp string, treated_sp_cq string, treated_sp_aq string, treated_other_anti string, treated_any_anti string, treated_antipyretic string, treated_antibiotic string,
      treated_other_drug string, treated_traditional string, treated_dontknow string, not_treated string
Note: Dummy reader just for schema
output_schema_20180828 (reader CSV2_3) [off]
    attributes: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

Bookmark: Run queries
FeatureMerger_10
    ATTR_ACCUM_MODE = Merge Supplier
    ATTR_CONFLICT_RES = Use Requestor
    CLEANING_TOLERANCE = None
    IGNORE_NULLS = No
    JOIN_KEYS = @Value(surveyid) @Value(SurveyId) AUTO
    MERGE_TYPE = Attributes Only
    PROCESS_DUPS = No
    REJECT_NULL_MISSING_KEYS = No
    SUPPLIERS_FIRST = Yes
    MERGED -> SQLExecutor_CHILD [INITIATOR]
    MERGED -> AttributeManager_3
    UNMERGED_REQUESTOR -> SQLExecutor_CHILD [INITIATOR]
    UNMERGED_REQUESTOR -> AttributeManager_3
SQLExecutor_CHILD
    COMBINE_ATTRS = Keep Result Attributes if Conflict
    COMBINE_GEOM = Initiator Geometry Only
    DATASET = DHS Data Readonly
    EXPOSED_ATTRIBUTE_LIST = child_num,clusterid,latitude,longitude,region,sample_wt,urban_rural,wealth_quint,woman_id,wt,treated_act,treated_act_al,treated_act_asaq,treated_act_asmq,treated_dhasp,treated_mono_as,treated_mono_am,treated_mono_arte,treated_aq,treated_cq,treated_qn,treated_pq,treated_mq,treated_sp,treated_sp_cq,treated_sp_aq,treated_other_anti,treated_any_anti,treated_antipyretic,treated_antibiotic,treated_other_drug,treated_traditional,treated_dontknow,not_treated
    FORMAT = POSTGRES
    POSTGRES_CREATE_FEATURE_TABLES_FROM_DATA = Yes
    POSTGRES_NAMED_CONNECTION = DHS Data Readonly
    POSTGRES_QUERY_FEATURE_TYPES_FOR_MERGE_FILTERS = Yes
    POSTGRES_READ_TIME_WITH_TIMEZONE = Yes
    SQL_STATEMENT = @Value(_outSQL)
    RESULT -> AttributeManager_15
    <REJECTED> -> LOG_Rejected_SQL
Note: LOG_Rejected_SQL
LOG_Rejected_SQL: Logger
    MAXCOORDS = 20
    MAXFEATS = 2000
    MESSAGE = Rejected SQL feature:

Bookmark: Save the SQL query file
AttributeManager_3
    ATTR_TABLE:
      SET_TO _sqlFN = @Value(surveyid).AM.ChildQuery.sql
      SET_TO _sqlPath = $(OutputFolder)\generated_sql\@Value(_sqlFN)
    -> AttributeFileWriter_2
AttributeFileWriter_2
    CHAR_ENCODING = fme-system
    FILE_NAME = @Value(_sqlPath)
    OVERWRITE_FILE = Overwrite file
    SOURCE_ATTR = _outSQL
