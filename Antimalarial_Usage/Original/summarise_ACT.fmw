FME workspace summarise_ACT.fmw

Parameters:
- REC01_CSV = C:\Users\zool1301\Documents\DHS\Phase6\ExtractedSurveyRecords_Python\IDIR62.REC01.csv   # Survey CSV for REC01
- REC21_CSV = C:\Users\zool1301\Documents\DHS\Phase6\ExtractedSurveyRecords_Python\IDIR62.REC21.csv   # Survey CSV for REC21
- REC43_CSV = C:\Users\zool1301\Documents\DHS\Phase6\ExtractedSurveyRecords_Python\IDIR62.REC43.csv   # Survey CSV for REC43
- RECML_CSV = C:\Users\zool1301\Documents\DHS\Phase6\ExtractedSurveyRecords_Python\IDIR62.RECML.csv   # Survey CSV for RECML
- MaxAge = 5   # Children less than or equal to age (yrs)
- SurveyRecordSpec = C:\Users\zool1301\Documents\DHS\Phase6\SurveySpecs_Final\IDIR62.FlatRecordSpec.csv   # Record spec file for survey (Generated with python script)
- DestDataset_FILEGDB = $(FME_MF_DIR)Outputs\Phase6_ACT_Test.gdb   # Destination Geodatabase for geographic (point and region) data
- AllPointShapes = C:\Users\zool1301\Documents\DHS\Phase6\ExtractedSurveysAndShapes\*.shp   # All survey point shapefiles
- OutCSVDir = $(FME_MF_DIR)Outputs   # Destination CSV Folder for tablular results
- SURVEY_GPS_FEAT_TYPE = N/A
- SurveyIDMap_CSV = C:\Users\zool1301\Documents\DHS\DHS_Info\SurveyIdsByFile_P6_All.csv   # Survey ID mapping CSV file
- Source_GDB_Boundaries = C:\Users\zool1301\Documents\DHS\DHS_Info\DHS_Boundary_Data\full_download\sdr_subnational_boundaries_all_surveys.gdb   # Source Geodatabase containing survey boundaries
- Use_ARI = 0   # Use ARI fields (H31*) in addition to H22
- DestDataset_GEODATABASE_FILE = $(FME_MF_DIR)Outputs\Phase6_ACT_Test_AO.gdb   # Destination Esri File Geodatabase
- SourceDataset_XLSXR = $(FME_MF_DIR)SupportingData\variable_selection_done.xlsx   # Source Microsoft Excel File(s)

Readers:
- CSV_1: CSV from $(REC21_CSV)
- CSV_2: CSV from $(REC43_CSV)
- CSV_3: CSV from $(REC01_CSV)
- CSV_4: CSV from $(REC01_CSV)
- CSV_5: CSV from $(RECML_CSV)
- CSV_6: CSV from $(RECML_CSV)
- CSV_7: CSV from $(SurveyRecordSpec)
- SHAPE_1: SHAPE from $(AllPointShapes)
- SHAPE_2: SHAPE from $(AllPointShapes)
- CSV_8: CSV from $(SurveyIDMap_CSV)
- FILEGDB_1: FILEGDB from $(Source_GDB_Boundaries)
- CSV_9: CSV from $(SurveyIDMap_CSV)
- XLSXR_1: XLSXR from $(SourceDataset_XLSXR)

Writers:
- FILEGDB_2: FILEGDB to $(DestDataset_FILEGDB)
- CSV_10: CSV to $(OutCSVDir)
- GEODATABASE_FILE_1: GEODATABASE_FILE to $(DestDataset_GEODATABASE_FILE)

CSV (reader CSV_6)
    attributes: CASEID char(9), IDXML number(2,0), ML0 number(2,0), ML1 number(3,0), ML2 number(2,0), ML11 char(1), ML12 char(1), ML13A number(2,0), ML13B number(2,0), ML13C number(2,0), ML13D number(2,0), ML13E number(2,0), ML13F char(1), ML13G char(1), ML13H number(2,0), ML13I number(2,0), ML13J number(2,0), ML13K number(2,0), ML13L number(2,0), ML13M number(2,0), ML13N char(1), ML13O char(1), ML13P char(1), ML13X number(2,0), ML13Y number(2,0), ML13Z number(2,0), ML14A char(1), ML14B char(1), ML14Y char(1), ML14Z char(1),
      ML15A char(1), ML15B char(1), ML15C char(1), ML16A number(2,0), ML16B char(1), ML16C char(1), ML17A number(2,0), ML17B char(1), ML17C char(1), ML18A char(1), ML18B char(1), ML18C char(1), ML19A char(1), ML19B char(1), ML19C char(1), ML19D char(1), ML19E char(1), ML19F char(1), ML19X char(1), ML19Y char(1), ML19Z char(1), ML20A number(2,0), ML20B char(1), ML20C char(1), ML21A char(1), ML21B char(1), ML21C char(1), ML22A char(1), ML22B char(1), ML22C char(1),
      ML23A number(2,0), ML23B char(1), ML23C char(1), ML24C char(1)
    -> FeatureMerger_8 [input 2]
Note: For each yes answer, see if it was to a question about ACT taken
FeatureMerger_4
    PROCESS_DUPS = No
    SUPPLIERS_FIRST = No
    JOIN_KEYS = @Value(_attr_name) @Value(recode) AUTO
    MERGE_TYPE = Attributes Only
    ATTR_CONFLICT_RES = Use Requestor
    ATTR_ACCUM_MODE = Merge Supplier
    IGNORE_NULLS = No
    MERGED -> Sampler
Note: take the first one we find (they all / have all fields of the original / unexploded feature too)
Sampler
    SAMPLE_TYPE_LONG = First N Features
    GROUP_BY = CASEID
    RATE = 1
    SAMPLED -> AttributeRemover
Note: Remove the crud and that's our filtered output for this sickness record
AttributeRemover
    REMOVE_ATTRS = _attr_name,_attr_value
    -> StatisticsCalculator_6
Note: count total ill kids who went to / selected treatment, by woman
StatisticsCalculator_6
    COMPUTE_HISTOGRAM = NO
    GROUP_BY = CASEID
    PREPEND_ATTR_NAME_CHOICE = For multiple results only
    COUNT_ATTR = fever_took_ACT_count
    STATS_ATTRS = CASEID
    SUMMARY -> FeatureMerger [input 2]
Note: For each yes answer, see if it was to a question about ACT timing
FeatureMerger_9
    PROCESS_DUPS = No
    SUPPLIERS_FIRST = No
    JOIN_KEYS = @Value(_attr_name) @Value(recode) AUTO
    MERGE_TYPE = Attributes Only
    ATTR_CONFLICT_RES = Use Requestor
    ATTR_ACCUM_MODE = Merge Supplier
    IGNORE_NULLS = No
    MERGED -> Sampler_3
Sampler_3
    SAMPLE_TYPE_LONG = First N Features
    GROUP_BY = CASEID
    RATE = 1
    SAMPLED -> AttributeRemover_2
AttributeRemover_2
    REMOVE_ATTRS = _attr_name,_attr_value
    -> StatisticsCalculator_7
StatisticsCalculator_7
    COMPUTE_HISTOGRAM = NO
    GROUP_BY = CASEID
    PREPEND_ATTR_NAME_CHOICE = For multiple results only
    COUNT_ATTR = fever_took_ACT_quickly_count
    STATS_ATTRS = CASEID
    SUMMARY -> FeatureMerger [input 2]
Note: For each yes answer, see if it was to a question about other antimalarial
FeatureMerger_10
    PROCESS_DUPS = No
    SUPPLIERS_FIRST = No
    JOIN_KEYS = @Value(_attr_name) @Value(recode) AUTO
    MERGE_TYPE = Attributes Only
    ATTR_CONFLICT_RES = Use Requestor
    ATTR_ACCUM_MODE = Merge Supplier
    IGNORE_NULLS = No
    MERGED -> Sampler_4
Sampler_4
    SAMPLE_TYPE_LONG = First N Features
    GROUP_BY = CASEID
    RATE = 1
    SAMPLED -> AttributeRemover_3
AttributeRemover_3
    REMOVE_ATTRS = _attr_name,_attr_value
    -> StatisticsCalculator_8
StatisticsCalculator_8
    COMPUTE_HISTOGRAM = NO
    GROUP_BY = CASEID
    PREPEND_ATTR_NAME_CHOICE = For multiple results only
    COUNT_ATTR = fever_took_other_AM_count
    STATS_ATTRS = CASEID
    SUMMARY -> FeatureMerger [input 2]

Bookmark: Parse record 01 - individual (woman) respondent
CSV (reader CSV_3)
    attributes: CASEID char(9), V000 char(4), V001 number(3,0), V002 number(3,0), V003 number(3,0), V004 number(3,0), V005 number(8,0), V006 number(2,0), V007 number(5,0), V008 number(5,0), V009 number(3,0), V010 number(5,0), V011 number(5,0), V012 number(3,0), V013 number(2,0), V014 number(2,0), V015 number(2,0), V016 number(3,0), V017 char(1), V018 number(2,0), V019 number(2,0), V019A number(2,0), V020 number(2,0), V021 number(3,0), V022 number(2,0), V023 number(2,0), V024 number(2,0), V025 number(2,0), V026 char(1), V027 number(2,0),
      V028 number(4,0), V029 number(3,0), V030 number(4,0), V031 number(3,0), V032 number(2,0), V033 char(1), V034 char(1), V040 number(5,0), V042 number(2,0), V043 char(1), V044 char(1)
    -> AttributeKeeper
Note: keep on ly the variables we're interested in
AttributeKeeper
    KEEP_ATTRS = CASEID,V000,V001,V002,V012,V024,V007
    -> REC01
    -> FeatureMerger [input 1]
REC01: Inspector [off]
Note: CSV: REC01 [CSV]
CSV (reader CSV_4) [off]
    attributes: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

Bookmark: Parse record 21 - individual children
Note: CSV: REC21 [CSV]
CSV (reader CSV_1)
    attributes: B3 number(5,0), B2 number(5,0), B1 number(3,0), B0 number(2,0), BORD number(2,0), CASEID char(9), B16 number(3,0), BIDX number(2,0), B15 number(2,0), B13 number(2,0), B12 number(4,0), B11 number(4,0), B10 number(2,0), B9 number(2,0), B8 number(3,0), B7 number(4,0), B6 number(4,0), B5 number(2,0), B4 number(2,0)
    -> REC21
    -> AttributeKeeper_2
AttributeKeeper_2
    KEEP_ATTRS = B5,B8,BIDX,BORD,CASEID
    -> Tester
Note: Child is alive?
Tester
    BOOL_OP = OR
    TEST_MODE = Automatic
    TEST_DESCRIPTION = ""
    TEST_CLAUSE = TEST @Value(B5) = 1
    PASSED -> StatisticsCalculator_3
    PASSED -> Tester_4
Note: count total live kids (Any age) / by woman
StatisticsCalculator_3
    COMPUTE_HISTOGRAM = NO
    GROUP_BY = CASEID
    PREPEND_ATTR_NAME_CHOICE = For multiple results only
    COUNT_ATTR = total_children_count
    STATS_ATTRS = CASEID
    SUMMARY -> FeatureMerger [input 2]
Note: Child is less than or equal specified age?
Tester_4
    BOOL_OP = OR
    TEST_MODE = Automatic
    TEST_DESCRIPTION = ""
    TEST_CLAUSE = TEST @Value(B8) <= $(MaxAge)
    PASSED -> StatisticsCalculator_5
    PASSED -> AttributeKeeper_4
Note: count total live young kids / by woman
StatisticsCalculator_5
    COMPUTE_HISTOGRAM = NO
    GROUP_BY = CASEID
    PREPEND_ATTR_NAME_CHOICE = For multiple results only
    COUNT_ATTR = total_young_count
    STATS_ATTRS = CASEID
    SUMMARY -> FeatureMerger [input 2]
AttributeKeeper_4
    KEEP_ATTRS = BIDX,CASEID
    -> FeatureMerger_3 [input 2]
REC21: Inspector [off]

Bookmark: Parse record 43 - illness incidents in children and RECML - malaria in children
Note: REC43: / Individual child health record
CSV (reader CSV_2)
    attributes: H12B number(2,0), H12C number(2,0), H12D number(2,0), H12E number(2,0), H12F number(2,0), H12G number(2,0), H12H number(2,0), H12I number(2,0), H12J number(2,0), H12K number(2,0), H12L number(2,0), H12M number(2,0), H12N number(2,0), H12O number(2,0), H12P number(2,0), H12Q char(1), H12R char(1), H12S number(2,0), H12T number(2,0), H12U number(2,0), H12V number(2,0), H12W char(1), H12X number(2,0), H12Y number(2,0), H12Z number(2,0), H13 number(2,0), H13B char(1), H14 number(2,0), H15 char(1), H15A char(1),
      H15B char(1), H15C char(1), H15D char(1), H15E char(1), H15F char(1), H15G char(1), H15H char(1), H15I char(1), H15J char(1), H15K char(1), H15L char(1), H15M char(1), H20 char(1), H21A char(1), H21 char(1), H22 number(2,0), H31 number(2,0), H31B number(2,0), H31C number(2,0), H31D number(2,0), H31E number(2,0), H32A number(2,0), H32B number(2,0), H32C number(2,0), H32D number(2,0), H32E number(2,0), H32F number(2,0), H32G number(2,0), H32H number(2,0), H32I number(2,0),
      H32J number(2,0), H32K number(2,0), H32L number(2,0), H32M number(2,0), H32N number(2,0), H32O number(2,0), H32P number(2,0), H32Q char(1), H32R char(1), H32S number(2,0), H32T number(2,0), H32U number(2,0), H32V number(2,0), H32W number(2,0), H32X number(2,0), H32Y number(2,0), H32Z number(2,0), H33 number(2,0), H33D number(3,0), H33M number(3,0), H33Y number(5,0), H34 number(2,0), H35 char(1), H36A number(2,0), H36B number(2,0), H36D number(2,0), H36E char(1), H36F char(1), H37A number(2,0), H37B number(2,0),
      H37C char(1), H37D number(2,0), H37E number(2,0), H37F char(1), H37G char(1), H37H number(2,0), H37I number(2,0), H37J number(2,0), H37K number(2,0), H37L number(2,0), H37M number(2,0), H37N number(2,0), H37O number(2,0), H37P number(2,0), H37X number(2,0), H37Y number(2,0), H37Z number(2,0), H38 number(2,0), H39 number(2,0), H40 char(1), H40D char(1), H40M char(1), H40Y char(1), H41A char(1), H41B char(1), H42 number(2,0), H43 number(2,0), H44A char(1), H44B char(1), H44C char(1),
      H45 char(1), H46A number(3,0), H46B char(1), H47 char(1), H5 number(2,0), HIDX number(2,0), H1 number(2,0), H2 number(2,0), H8D number(3,0), H2D number(3,0), H2M number(3,0), H2Y number(5,0), H3 number(2,0), H3D number(3,0), H3M number(3,0), H3Y number(5,0), H4 number(2,0), H4D number(3,0), H4M number(3,0), H4Y number(5,0), H12A number(2,0), H5D number(3,0), H5M number(3,0), H5Y number(5,0), H6 number(2,0), H6D number(3,0), H6M number(3,0), H6Y number(5,0), H7 number(2,0), H7D number(3,0),
      H7M number(3,0), H7Y number(5,0), H8 number(2,0), H0 number(2,0), H9Y number(5,0), H9M number(3,0), H9D number(3,0), H9 number(2,0), H8Y number(5,0), H8M number(3,0), H36C number(2,0), CASEID char(9), H0D number(2,0), H0M number(3,0), H0Y number(5,0), H10 number(2,0), H11 number(2,0), H11B number(2,0)
    -> AttributeKeeper_3
AttributeKeeper_3
    KEEP_ATTRS = CASEID,H22,H31,H31B,H31C,H32A,H32B,H32C,H32D,H32E,H32F,H32G,H32H,H32I,H32J,H32K,H32L,H32M,H32N,H32O,H32P,H32Q,H32R,H32S,H32T,H32U,H32V,H32W,H32X,H32Y,H32Z,HIDX
    -> Tester_2
Note: Currently only checking H22 as all surveys were found to cover it
Note: Had fever in last 2 weeks / OR, (Optionally IIF parameter set) / Had cough AND (short breath OR probs in chest)
Tester_2
    BOOL_OP = COMPOSITE
    TEST_MODE = Automatic
    COMPOSITE_TEST = "1 OR (5 AND 2 AND (3 OR 4))"
    TEST_DESCRIPTION = ""
    TEST_CLAUSE:
      TEST @Value(H22) = 1
      TEST @Value(H31) BETWEEN 1,7
      TEST @Value(H31B) BETWEEN 1,7
      TEST @Value(H31C) BETWEEN 1,7
      TEST $(Use_ARI) = 1
    PASSED -> FeatureMerger_3 [input 1]
Note: ensure that illness record pertains / to a child below specified age (which it will / if age=5 but may not if age < 5)
FeatureMerger_3
    PROCESS_DUPS = No
    SUPPLIERS_FIRST = No
    JOIN_KEYS = @Value(CASEID) @Value(CASEID) AUTO @Value(HIDX) @Value(BIDX) AUTO
    MERGE_TYPE = Attributes Only
    ATTR_CONFLICT_RES = Use Requestor
    ATTR_ACCUM_MODE = Merge Supplier
    IGNORE_NULLS = No
    MERGED -> StatisticsCalculator
    NOT_MERGED -> IllnessRecordsChildTooOld
    MERGED -> AttributeKeeper_6
Note: count total ill kids by woman
StatisticsCalculator
    COMPUTE_HISTOGRAM = NO
    GROUP_BY = CASEID
    PREPEND_ATTR_NAME_CHOICE = For multiple results only
    COUNT_ATTR = fever_young_count
    STATS_ATTRS = CASEID
    SUMMARY -> FeatureMerger [input 2]
AttributeKeeper_6
    KEEP_ATTRS = BIDX,CASEID,H22,HIDX
    -> FeatureMerger_8 [input 1]
IllnessRecordsChildTooOld: Inspector
Note: Attach the malaria specific items to the child health record item
FeatureMerger_8
    PROCESS_DUPS = No
    SUPPLIERS_FIRST = No
    JOIN_KEYS = @Value(BIDX) @Value(IDXML) AUTO @Value(CASEID) @Value(CASEID) AUTO
    MERGE_TYPE = Attributes Only
    ATTR_CONFLICT_RES = Use Requestor
    ATTR_ACCUM_MODE = Merge Supplier
    IGNORE_NULLS = No
    MERGED -> AttributeExploder
Note: Separate each illness record into a new feature / (record) for each of the variables (fields) that / can define the treatment. i.e. normalise it
AttributeExploder
    ATTR_NAME_LABEL = _attr_name
    ATTR_VALUE_LABEL = _attr_value
    EXPLODING_TYPE = Features
    KEEP_GEOMETRY = No
    KEEP_ATTRIBUTES = Yes
    -> Tester_6
Note: Keep if it's 1 (that question was answered yes) in this illness record
Tester_6
    BOOL_OP = OR
    TEST_MODE = Automatic
    TEST_DESCRIPTION = ""
    TEST_CLAUSE = TEST @Value(_attr_value) = 1
    PASSED -> FeatureMerger_4 [input 1]
    PASSED -> FeatureMerger_9 [input 1]
    PASSED -> FeatureMerger_10 [input 1]
Note: RECML: / Individual child malaria record
CSV (reader CSV_5) [off]
    attributes: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

Bookmark: Work out which of the antimalarial variables we want to look at to define treatment
Note: RecordSpec for the overall survey, / gives the survey-specific labels allocated to each H32* variable. Generated by the DCF parser. This info is now in the database so could be read from there. The main reason for reading it here now is to get the file (survey) code to filter the interpretation spreadsheet.
CSV (reader CSV_7)
    attributes: FileCode char(7), RecordName char(6), RecordTypeValue char(4), Name char(6), Label char(65), Start number(4,0), Len number(3,0), Occurrences char(1), FMETYPE char(13)
    -> VariableSetter
VariableSetter
    VALUE = @Value(FileCode)
    SCOPE = Global
    VARNAME = currentFileCode
    -> Sampler_2
Note: Simplify, keep only the name of attributes / that we want to keep (And test)
AttributeKeeper_5
    KEEP_ATTRS = recode
    -> FeatureMerger_4 [input 2]
    -> AttributeKeeper_5_Output
AttributeKeeper_5_Output: Inspector [off]
AttributeKeeper_7
    KEEP_ATTRS = recode
    -> FeatureMerger_9 [input 2]
AttributeKeeper_8
    KEEP_ATTRS = recode
    -> FeatureMerger_10 [input 2]

Bookmark: Interpret antimalarial questions manually via external spreadsheet
Note: External spreadsheet has been generated containing all variable names / labels from the malaria table. This has been manually flagged to indicate for each variable whether it should be interpreted as "ACT taken", "Other antimalarial taken", "ACT taken within 24 hours", if the data file contains a response to that question.
Sampler_2
    SAMPLE_TYPE_LONG = First N Features
    GROUP_BY = FileCode
    RATE = 1
    SAMPLED -> FeatureMerger_5 [input 2]
Note: Spreadsheet specifying question interpretations
Sheet1 (reader XLSXR_1)
    attributes: survey char(7), record char(6), record name char(8), recode char(6), recode desc char(74), CountAsACTTiming char(26), CountAsACTTaken char(26)
    -> FeatureMerger_5 [input 1]
Note: Get the ones relating to this survey
FeatureMerger_5
    PROCESS_DUPS = No
    SUPPLIERS_FIRST = Yes
    JOIN_KEYS = @Value(survey) @Value(FileCode) AUTO
    MERGE_TYPE = Attributes Only
    ATTR_CONFLICT_RES = Use Requestor
    ATTR_ACCUM_MODE = Merge Supplier
    IGNORE_NULLS = No
    MERGED -> Tester_7
Note: Does this variable represent an "ACT taken" question?
Note: We should only have Y in 1 column!
Tester_7
    BOOL_OP = OR
    TEST_MODE = Automatic
    TEST_DESCRIPTION = ""
    TEST_CLAUSE = TEST @LowerCase(@Value(CountAsACTTaken)) = y
    PASSED -> AttributeKeeper_5
    FAILED -> Tester_8
Note: Does this variable represent an "ACT within 24 hrs of onset" question?
Tester_8
    BOOL_OP = OR
    TEST_MODE = Automatic
    TEST_DESCRIPTION = ""
    TEST_CLAUSE = TEST @LowerCase(@Value(CountAsACTTiming)) = y
    FAILED -> Tester_9
    PASSED -> AttributeKeeper_7
Note: TODO (Not yet in spreadsheet) Does this variable represent an "other antimalarial taken" question?
Tester_9
    BOOL_OP = OR
    TEST_MODE = Automatic
    TEST_DESCRIPTION = ""
    TEST_CLAUSE = TEST @LowerCase(@Value(CountAsACTTiming)) = y
    PASSED -> AttributeKeeper_8

Bookmark: Accumulate results by individual woman
Note: Attach each of the different child summaries to each woman. / Each has a different variable name so we allow multiple suppliers to attach them all
FeatureMerger
    PROCESS_DUPS = Yes
    SUPPLIERS_FIRST = No
    GEOM_TYPE = Build Polygons
    JOIN_KEYS = @Value(CASEID) @Value(CASEID) AUTO
    MERGE_TYPE = Attributes Only
    ATTR_CONFLICT_RES = Use Requestor
    ATTR_ACCUM_MODE = Merge Supplier
    IGNORE_NULLS = No
    MERGED -> AttributeCreator
    MERGED -> Tester_3
    MERGED -> StatisticsCalculator_4
    MERGED -> StatisticsCalculator_2

Bookmark: Accumulate and summarise by cluster (point location)
Note: summarise by cluster (V001), also grouping by country (V000) and region (V024) so that these carry thru
StatisticsCalculator_4
    SUM_ATTR = _sum
    COMPUTE_HISTOGRAM = NO
    GROUP_BY = V000 V001 V024
    PREPEND_ATTR_NAME_CHOICE = For multiple results only
    STATS_ATTRS = fever_young_count total_children_count total_young_count fever_took_ACT_count fever_took_ACT_quickly_count fever_took_other_AM_count
    SUMMARY -> AttributeCreator_2
Note: Calculate proportional results from sums
AttributeCreator_2
    ATTR_LIST = fever_prop_by_cluster,@Evaluate(@Value(fever_young_count._sum)/@Value(total_young_count._sum)),fever_took_ACT_prop_by_cluster,@Evaluate(@Value(fever_took_ACT_count._sum)/@Value(fever_young_count._sum)),fever_took_ACT_quickly_prop_by_cluster,@Evaluate(@Value(fever_took_ACT_quickly_count._sum)/@Value(fever_young_count._sum)),fever_took_other_AM_prop_by_cluster,@Evaluate(@Value(fever_took_other_AM_count._sum)/@Value(fever_young_count._sum))
    -> AttributeRenamer
AttributeRenamer
    ATTR_LIST = fever_young_count._sum,fever_occurrence_count_by_cluster,,total_children_count._sum,total_children_count_by_cluster,,total_young_count._sum,total_young_count_by_cluster,,V001,clusterid,,V024,region_v024,,V000,ctry_phase,
    -> Results_by_cluster
    -> VariableRetriever
Results_by_cluster: Inspector
VariableRetriever
    SCOPE = Global
    VALUE_ATTR = filecode
    VARNAME = currentFileCode
    -> AttributeCreator_3
Note: Set output names for dynamic writers
AttributeCreator_3
    ATTR_LIST = outTableName,@Value(filecode)_Fever_By_Cluster_Table,outFCClusterName,@Value(filecode)_Fever_By_Cluster
    -> File1 (writer CSV_10)
    -> FeatureMerger_2 [input 2]
Note: Write CSV output results (always)
File1 (writer CSV_10)
    attributes: filecode text, region_v024 text, clusterid int, total_children_count_by_cluster int, total_young_count_by_cluster int, fever_occurrence_count_by_cluster int, fever_prop_by_cluster float, fever_took_ACT_prop_by_cluster float, fever_took_ACT_quickly_prop_by_cluster float, fever_took_other_AM_prop_by_cluster float
Note: Read the points shapefile for the required survey if one exists
BDGE61FL (reader SHAPE_2)
    attributes: DHSID char(254), DHSCC char(254), DHSYEAR number(16,6), DHSCLUST number(16,6), CCFIPS char(254), ADM1FIPS char(254), ADM1FIPSNA char(254), ADM1SALBNA char(254), ADM1SALBCO char(254), ADM1DHS number(16,6), ADM1NAME char(254), DHSREGCO number(16,6), DHSREGNA char(254), SOURCE char(254), URBAN_RURA char(254), LATNUM number(16,6), LONGNUM number(16,6), ALT_GPS number(16,6), ALT_DEM number(16,6), DATUM char(254)
    -> AttributeExposer
AttributeExposer
    ATTR_LIST = fme_basename
    -> FeatureMerger_2 [input 1]
Note: NB / It is the responsibility of the user or caller to ensure the correct shapefile feature type name is provided. / The match is only done on cluster id which isn't unique between different surveys! A dummy value such as N/A must be provided if / no point shapefile is available otherwise it will read all!
FeatureMerger_2
    PROCESS_DUPS = No
    SUPPLIERS_FIRST = No
    JOIN_KEYS = @Value(DHSCLUST) @Value(clusterid) AUTO
    MERGE_TYPE = Attributes Only
    ATTR_CONFLICT_RES = Use Requestor
    ATTR_ACCUM_MODE = Merge Supplier
    IGNORE_NULLS = No
    MERGED -> Results_Geographic
    MERGED -> FeatureClass1 (writer FILEGDB_2)
    MERGED -> FeatureClass1 (writer GEODATABASE_FILE_1)
FeatureClass1 (writer GEODATABASE_FILE_1)
    attributes: filecode char(7), total_children_count_by_cluster integer, total_young_count_by_cluster integer, fever_occurrence_count_by_cluster integer, fever_prop_by_cluster double(20,10), fever_took_ACT_prop_by_cluster double(20,10), fever_took_ACT_quickly_prop_by_cluster double(20,10), fever_took_other_AM_prop_by_cluster double(20,10)
Note: Write point featureclass results if any
FeatureClass1 (writer FILEGDB_2)
    attributes: filecode text(12), total_children_count_by_cluster int, total_young_count_by_cluster int, fever_occurrence_count_by_cluster int, fever_prop_by_cluster double, fever_took_ACT_prop_by_cluster double, fever_took_ACT_quickly_prop_by_cluster double, fever_took_other_AM_prop_by_cluster double
Results_Geographic: Inspector

Bookmark: View or save individual results
AttributeCreator [off]
    ATTR_LIST = poorly_prop_by_woman,@Evaluate(@Value(fever_young_count)/@Value(total_young_count))
    -> ResultsByIndividual [off]
ResultsByIndividual: Inspector [off]

Bookmark: Individual summary check
Note: If total young count > 6 then health record doesn't / cover all children (there are a max of 6 health records)
Tester_3
    BOOL_OP = OR
    TEST_MODE = Automatic
    TEST_DESCRIPTION = ""
    TEST_CLAUSE = TEST @Value(total_young_count) > 6
    PASSED -> WarningNotAllHealthRecordsPresent
WarningNotAllHealthRecordsPresent: Inspector

Bookmark: Accumulate and summarise by region (polygon)
Note: summarise by region V024, also grouping by country V000 so that these carry thru
StatisticsCalculator_2
    SUM_ATTR = _sum
    COMPUTE_HISTOGRAM = NO
    GROUP_BY = V000 V024
    PREPEND_ATTR_NAME_CHOICE = For multiple results only
    STATS_ATTRS = fever_took_ACT_count fever_young_count total_children_count total_young_count fever_took_ACT_quickly_count fever_took_other_AM_count
    SUMMARY -> AttributeCreator_4
Note: Calculate proportional results from sums
AttributeCreator_4
    ATTR_LIST = fever_prop_by_region,@Evaluate(@Value(fever_young_count._sum)/@Value(total_young_count._sum)),fever_took_ACT_prop_by_region,@Evaluate(@Value(fever_took_ACT_count._sum)/@Value(fever_young_count._sum)),fever_took_ACT_quickly_prop_by_region,@Evaluate(@Value(fever_took_ACT_quickly_count._sum)/@Value(fever_young_count._sum)),fever_took_other_AM_prop_by_region,@Evaluate(@Value(fever_took_other_AM_count._sum)/@Value(fever_young_count._sum))
    -> AttributeRenamer_2
AttributeRenamer_2
    ATTR_LIST = fever_young_count._sum,fever_occurrence_count_by_region,,total_children_count._sum,total_children_count_by_region,,total_young_count._sum,total_young_count_by_region,,V024,region_v024,,V000,ctry_phase,
    -> VariableRetriever_2
VariableRetriever_2
    SCOPE = Global
    VALUE_ATTR = filecode
    VARNAME = currentFileCode
    -> AttributeCreator_7
Note: Set output name for dynamic writer
AttributeCreator_7
    ATTR_LIST = outFCRegionName,@Value(filecode)_Fever_By_Region
    -> FeatureMerger_6 [input 1]
Note: Read DHS survey identifier mapping file (provided by DHS and modified) to / work out which polygons are associated with this survey file
CSV (reader CSV_9)
    attributes: SurveyFilename char(7), Country char(22), Year char(8), Survey_ID_num number(4,0), SurveyAPI_ID char(10), Type char(4)
    -> FeatureMerger_6 [input 2]
    -> _All_
_All_: Inspector [off]
Note: Read all DHS boundaries (downloaded and combined previously)
dhs_subnational_boundaries_all_surveys (reader FILEGDB_1)
    attributes: OBJECTID objectid, ISO text(2), FIPS text(2), DHSCC text(2), SVYTYPE text(3), SVYYEAR double, CNTRYNAMEE text(254), CNTRYNAMEF text(254), CNTRYNAMES text(254), DHSREGEN text(254), DHSREGFR text(254), DHSREGSP text(254), SVYID double, REG_ID text(15), Svy_Map text(3), MULTLEVEL text(3), LEVELRNK double, REGVAR text(254), REGCODE double, REGNAME text(254), OTHREGVAR text(254), OTHREGCO double, OTHREGNA text(254), LEVELCO text(254), LEVELNA text(254), REPALLIND text(254), REGNOTES text(254), SVYNOTES text(254), Shape_Length double, Shape_Area double
    -> FeatureMerger_7 [input 1]
SurveyIdsByFile (reader CSV_8) [off]
    attributes: SurveyFilename char(7), Country char(26), Year char(8), Survey_ID_num number(4,0), SurveyAPI_ID char(10), Type char(4)
    -> FeatureMerger_6 [input 2]
Note: From the survey filename e.g. BDIR61 get the numeric DHS survey identifier as used in the regional boundaries
FeatureMerger_6
    PROCESS_DUPS = No
    SUPPLIERS_FIRST = No
    JOIN_KEYS = @LowerCase(@Value(filecode)) @LowerCase(@Value(SurveyFilename)) AUTO
    MERGE_TYPE = Attributes Only
    ATTR_CONFLICT_RES = Use Requestor
    ATTR_ACCUM_MODE = Merge Supplier
    IGNORE_NULLS = No
    MERGED -> FeatureMerger_7 [input 2]
    NOT_MERGED -> FeatureMerger_6_NotMerged
FeatureMerger_6_NotMerged: Inspector
Note: Attach results to boundaries by matching survey id
FeatureMerger_7
    PROCESS_DUPS = No
    SUPPLIERS_FIRST = No
    JOIN_KEYS = @Value(SVYID) @Value(Survey_ID_num) AUTO @Value(REGCODE) @Value(region_v024) AUTO
    MERGE_TYPE = Attributes Only
    ATTR_CONFLICT_RES = Use Requestor
    ATTR_ACCUM_MODE = Merge Supplier
    IGNORE_NULLS = No
    MERGED -> FeatureClass100 (writer FILEGDB_2)
    MERGED -> FeatureMerger_7_Merged
Note: Write polygon featureclass results if any
FeatureClass100 (writer FILEGDB_2)
    attributes: filecode text(12), total_children_count_by_region int, total_young_count_by_region int, fever_occurrence_count_by_region int, fever_prop_by_region double, fever_took_ACT_prop_by_region double, fever_took_ACT_quickly_prop_by_region double, fever_took_other_AM_prop_by_region double
FeatureMerger_7_Merged: Inspector [off]
