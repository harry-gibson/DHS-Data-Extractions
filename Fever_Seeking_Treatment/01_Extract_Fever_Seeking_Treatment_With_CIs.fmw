FME workspace 01_Extract_Fever_Seeking_Treatment_With_CIs.fmw
Startup Python:
      # GBD - Archive outputs from any previous run
      # This script should be run as a startup script in any GBD stages that are run using FME
      import fme
      import os, glob, datetime, shutil

      # build the paths based on the template stage folder layout relative to where the workbench itself is
      # Use abspath because fme occasionally does some weird escaping syntax on FME_MF_DIR
      codepath = os.path.abspath(fme.macroValues['FME_MF_DIR'])
      rootpath = os.path.dirname(codepath)
      checkpoint_path = os.path.join(rootpath, 'Checkpoint_Outputs')
      intermediate_path = os.path.join(rootpath, 'Intermediary_Outputs')
      archive_path = os.path.join(checkpoint_path, 'Archive')
      runArchival = fme.macroValues['ArchiveLastOutputs']

      prev_run_metadata_file = os.path.join(checkpoint_path, 'last_run_metadata.txt')
      if os.path.exists(prev_run_metadata_file) and runArchival=='Yes':
          with open(prev_run_metadata_file, 'r') as f:
              prevRunTag = f.readline().strip()
          # move them to a new subfolder under the archive named by runtime
          outdir = os.path.join(archive_path, prevRunTag)
          outdir_intermediate = os.path.join(outdir, "intermediates")
          outdir_coding = os.path.join(outdir, "value_mapping")
          outdir_out = os.path.join(outdir, "output")
          os.makedirs(outdir_out)
          os.makedirs(outdir_coding)
          os.makedirs(outdir_intermediate)
          # move everything except the readme file and the archive folder itself
          checkpoint_wildcard = os.path.join(checkpoint_path, '*')
          intermediate_wildcard = os.path.join(intermediate_path, '*')
          to_move = [f for f in glob.glob(checkpoint_wildcard)
              if not (os.path.basename(f).lower().startswith('readme'))
              and not (os.path.basename(f).lower() == 'archive')]
          for f in to_move:
              try:
                  os.rename(f, os.path.join(outdir, os.path.basename(f)))
              except WindowsError:
                  print("Error moving " + f)
                  #raise
          to_move = [f for f in glob.glob(intermediate_wildcard)
              if not (os.path.basename(f).lower().startswith('readme'))
              and not (os.path.basename(f).lower() == 'archive')]
          for f in to_move:
              try:
                  os.rename(f, os.path.join(outdir_intermediate, os.path.basename(f)))
              except WindowsError:
                  print("Error moving " + f)
                  #raise
          coding_file = os.path.abspath(fme.macroValues['FeverQuestionMappingFile'])
          coding_file_out = os.path.join(outdir_coding, os.path.basename(coding_file))
          try:
              shutil.copy(coding_file, coding_file_out)
          except WindowsError:
                  print("Error copying " + coding_file)
                  #raise

      else:
          # check if there are any outputs there- the folder might be clean so no problem
          existing_files = glob.glob(os.path.join(checkpoint_path, '*.csv'))
          existing_files.extend(glob.glob(os.path.join(intermediate_path, '*.sql')))

          if len(existing_files) > 0 and runArchival == 'No':
              # cause an error
              logger = open(FME_LogFileName,'a')
              errMsg = ("Previous output data found but cannot find previous run metadata file or archival "
                  +"option was set to not run. Please archive manually to continue!")
              logger.write(errMsg)
              raise Exception(errMsg)

Parameters:
- FeverQuestionMappingFile = \\map-fs1.ndph.ox.ac.uk\map_data\DHS_Automation\Processing\FST_2019\Info\Fever_Question_Mapping_20190528_all_KB.csv
- ArchiveLastOutputs = Yes
- DHS_Survey_Listing_API = http://api.dhsprogram.com/rest/dhs/surveys?f=csv   # CSV retrieved from DHS API listing survey info - use API endpoint or local file
- IntermediateOutputFolder = ..\Intermediary_Outputs   # Output folder - for GBD should be relative path to the stage Intermediary_Outputs folder
- CheckpointOutputsFolder = ..\Checkpoint_Outputs   # Output folder - for GBD should be relative path to the stage Checkpoint_Outputs folder

Readers:
- CSV2_1: CSV2 from $(DHS_Survey_Listing_API)
- CSV2_2: CSV2 from $(FeverQuestionMappingFile)

Writers:
- CSV2_3: CSV2 to $(CheckpointOutputsFolder)

CSV (reader CSV2_2)
    attributes: surveyid string, NewPublicTreat string, NewAnyTreat string, label string, in_new string, old_public string, old_any string, in_old string, RecordName string, Name string
    -> Tester_8
    -> AttributeRenamer
AttributeRenamer
    ATTR_TABLE:
      RENAME_SET_DEFAULT NewAnyTreat > _any_treat
      RENAME_SET_DEFAULT NewPublicTreat > _public_treat
    -> StringCaseChanger
StringCaseChanger
    ATTRCHOICE = Selected Attributes
    ATTRLIST = _any_treat _public_treat
    CHANGE_TYPE = lowercase
    -> AttributeKeeper_2
    -> Sampler
Sampler
    GROUP_BY = surveyid
    RATE = 1
    SAMPLE_MODE = No
    SAMPLE_TYPE_LONG = First N Features
    SAMPLED -> AttributeKeeper
AttributeKeeper
    KEEP_ATTRS = surveyid
    -> FeatureMerger [REQUESTOR]
    -> FeatureMerger_2 [REQUESTOR]
    -> Junction
Note: Send one feature per survey forward, to the featuremerger where we will attach the queries we're about to build
Junction
    -> Junction_2
Note: One feature per survey
Junction_2
    -> FeatureMerger_3 [REQUESTOR]
AttributeKeeper_2
    KEEP_ATTRS = Label,Name,RecordName,surveyid,_any_treat,_public_treat
    -> AttributeCreator
Note: Every column flagged to use will go into a query in the form H32A::Integer=1. Format this.
AttributeCreator
    ATTR_TABLE:
      SET_TO _qualColumn = tblfever.@LowerCase(@Value(Name))::Integer=1
      SET_TO _feverTableJoinCol = FME_CONDITIONAL:DEFAULT_VALUE'XXXX'BOOL_OP;OR;COMPOSITE_TEST;<Unused>;TEST @Value(RecordName) = REC43'HIDX'BOOL_OP;OR;COMPOSITE_TEST;<Unused>;TEST @Value(RecordName) = REC4A'HIDXA'FME_NUM_CONDITIONS3___
    -> Tester_2
    -> Tester
Tester
    BOOL_OP = AND
    TEST_CLAUSE:
      TEST @Value(_any_treat) = y
      TEST @UpperCase(@Value(Name)) != H32Z
    PASSED -> FeatureMerger [SUPPLIER]
Note: The any-treat selector
Junction_4
    -> FeatureMerger_3 [SUPPLIER]
Tester_2
    BOOL_OP = AND
    TEST_CLAUSE:
      TEST @Value(_public_treat) = y
      TEST @UpperCase(@Value(Name)) != H32Z
    PASSED -> Tester_5
Tester_5
    BOOL_OP = OR
    TEST_CLAUSE = TEST @Value(_feverTableJoinCol) != XXXX
    PASSED -> FeatureMerger_2 [SUPPLIER]
    FAILED -> Non_Standard_Table_Rerun
Note: The public-treat selector
Junction_6
    -> FeatureMerger_3 [SUPPLIER]
Non_Standard_Table_Rerun: Inspector
Tester_8
    BOOL_OP = OR
    TEST_CLAUSE = TEST @Value(surveyid) IN 50,156,264

Bookmark: Build the H32*=1 condition lists for each treatment category
FeatureMerger
    ATTR_ACCUM_MODE = Merge Supplier
    ATTR_CONFLICT_RES = Use Requestor
    CLEANING_TOLERANCE = None
    IGNORE_NULLS = No
    JOIN_KEYS = @Value(surveyid) @Value(surveyid) AUTO
    LIST_ATTRS_TO_INCLUDE = _qualColumn RecordName
    LIST_NAME = any_treat
    MERGE_TYPE = Attributes Only
    PROCESS_DUPS = No
    REJECT_NULL_MISSING_KEYS = No
    SUPPLIERS_FIRST = No
    MERGED -> AttributeRemover
AttributeRemover
    REMOVE_ATTRS = Label,_qualColumn,Name,_any_treat,_public_treat
    -> ListConcatenator
ListConcatenator
    DROP_EMPTY_PARTS = No
    LIST_ATTR = any_treat{}._qualColumn
    SEP = " OR "
    VAL_ATTR = _anyClause
    -> Junction_3
    -> ListElementCounter
    -> ListDuplicateRemover
Note: Send the list of any-treatment clauses forward to merge onto the survey feature
Junction_3
    -> Junction_4
ListDuplicateRemover
    SRC_LIST = any_treat{}.RecordName
    -> ListElementCounter_3
ListElementCounter_3
    CNT_ATTR = _element_count
    LIST_NAME = any_treat{}
    -> Tester_6
Tester_6
    BOOL_OP = OR
    TEST_CLAUSE = TEST @Value(_element_count) > 1
    PASSED -> MoreThanOneFeverTable
Note: Check that for each survey we are only joining one fever table (REC43 or REC4A but not both) and that we don't have >26 values defined (H32A-Z
MoreThanOneFeverTable: Inspector
ListElementCounter
    CNT_ATTR = _element_count
    LIST_NAME = any_treat{}
    -> Tester_3
Tester_3
    BOOL_OP = OR
    TEST_CLAUSE = TEST @Value(_element_count) <= 26
    FAILED -> Too_Many_Any_Clauses
Too_Many_Any_Clauses: Inspector
FeatureMerger_2
    ATTR_ACCUM_MODE = Merge Supplier
    ATTR_CONFLICT_RES = Use Requestor
    CLEANING_TOLERANCE = None
    IGNORE_NULLS = No
    JOIN_KEYS = @Value(surveyid) @Value(surveyid) AUTO
    LIST_ATTRS_TO_INCLUDE = _qualColumn RecordName
    LIST_NAME = public_treat
    MERGE_TYPE = Attributes Only
    PROCESS_DUPS = No
    REJECT_NULL_MISSING_KEYS = No
    SUPPLIERS_FIRST = No
    MERGED -> AttributeRemover_2
AttributeRemover_2
    REMOVE_ATTRS = Label,_qualColumn,Name,_any_treat,_public_treat
    -> ListConcatenator_2
ListConcatenator_2
    DROP_EMPTY_PARTS = No
    LIST_ATTR = public_treat{}._qualColumn
    SEP = " OR "
    VAL_ATTR = _publicClause
    -> Junction_5
    -> ListElementCounter_2
    -> ListDuplicateRemover_2
Note: Send the list of public-treatment clauses forward to merge onto the survey feature
Junction_5
    -> Junction_6
ListDuplicateRemover_2
    SRC_LIST = public_treat{}.RecordName
    -> ListElementCounter_4
ListElementCounter_4
    CNT_ATTR = _element_count
    LIST_NAME = public_treat{}
    -> Tester_7
Tester_7
    BOOL_OP = OR
    TEST_CLAUSE = TEST @Value(_element_count) > 1
    PASSED -> MoreThanOneFeverTable_2
MoreThanOneFeverTable_2: Inspector
ListElementCounter_2
    CNT_ATTR = _element_count
    LIST_NAME = public_treat{}
    -> Tester_4
Tester_4
    BOOL_OP = OR
    TEST_CLAUSE = TEST @Value(_element_count) <= 26
    FAILED -> Too_Many_Public_Clauses
Too_Many_Public_Clauses: Inspector

Bookmark: Build and run the queries
FeatureMerger_3
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(surveyid) @Value(surveyid) AUTO
    MERGE_TYPE = Attributes Only
    PROCESS_DUPS = Yes
    REJECT_NULL_MISSING_KEYS = No
    SUPPLIERS_FIRST = No
    MERGED -> AttributeCreator_2
Note: Child-level / No proportion for child, obvs
AttributeManager_CHILD
    ATTR_TABLE:
      REMOVE _childQuery
      REMOVE _wmnQuery
      REMOVE _clustQuery
      REMOVE _regionQuery
      REMOVE _nationalQuery
      REMOVE any_treat
      REMOVE had_fever
      REMOVE public_treat
    -> FeatureMerger_8 [REQUESTOR]

Bookmark: Build the queries for each survey
Note: Build the subquery for selecting the actual fever results
AttributeCreator_2
    ATTR_TABLE:
      SET_TO _feverQuery = (SELECT
        surveyid
        , caseid
        -- either HIDX or HIDXA depending on whether we are reading REC43 or REC4A
        , @Value(_feverTableJoinCol)
        , CASE WHEN tblfever.h22::Integer = 1 THEN 1 ELSE 0 END as had_fever
        , CASE WHEN tblfever.h22::Integer = 1 AND (
         @Value(_anyClause)
        ) THEN 1 ELSE 0 END AS any_treat
        , CASE WHEN tblfever.h22::Integer = 1 AND (
         @Value(_publicClause)
         ) THEN 1 ELSE 0 END AS public_treat
        FROM dhs_data_tables."@Value(RecordName)" tblfever
        ) fever
    -> AttributeCreator_3
Note: Build the overall queries for selecting each level of results
AttributeCreator_3
    ATTR_TABLE:
      SET_TO _childQuery = SELECT
        r21.bidx as child_num
        , r01.caseid as woman_id
        , r01.v001 as clusterid
        , r01.v024 as region
        , r01.v005 as wt
        , clust.latnum as latitude
        , clust.longnum as longitude
        , h0.hv025 as urban_rural
        , r11.v190 as wealth_quint
        , 1 as young_child
        , r01.v005::Float / 1000000 as young_child_wt
        , (had_fever) had_fever
        , (case when had_fever=1 THEN r01.v005::Float / 1000000 ELSE 0 END) as had_fever_wt
        , (any_treat) any_treat
        , (case when any_treat=1 THEN r01.v005::Float / 1000000 ELSE 0 END) as any_treat_wt
        , (public_treat) public_treat
        , (case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
         dhs_data_tables."REC11" r11
        ON r01.surveyid::INTEGER = r11.surveyid::Integer AND r01.caseid = r11.caseid
        LEFT OUTER JOIN
        dhs_data_tables."RECH0" h0
        	-- dirty, but this is how it works
        	ON r01.surveyid = h0.surveyid AND LEFT(r01.caseid, -3) = h0.hhid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        ORDER BY r21.surveyid::Integer, r01.v024::Integer, r01.v001::Integer, r01.caseid, r21.bidx::Integer
      SET_TO _wmnQuery = SELECT
        r01.caseid as woman_id
        , r01.v001 as clusterid
        , r01.v024 as region
        , clust.latnum as latitude
        , clust.longnum as longitude
        , h0.hv025 as urban_rural
        , r11.v190 as wealth_quint
        , sum(1) as young_child
        , sum(r01.v005::Float / 1000000) as young_child_wt
        , sum(had_fever) had_fever
        , sum(case when had_fever=1 THEN r01.v005::Float / 1000000 ELSE 0 END) as had_fever_wt
        , sum(any_treat) any_treat
        , sum(case when any_treat=1 THEN r01.v005::Float / 1000000 ELSE 0 END) as any_treat_wt
        , sum(public_treat) public_treat
        , sum(case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
        dhs_data_tables."REC11" r11
        ON r01.surveyid::Integer = r11.surveyid::Integer AND r01.caseid = r11.caseid
        LEFT OUTER JOIN
        dhs_data_tables."RECH0" h0
        	-- dirty, but this is how it works
        	ON r01.surveyid = h0.surveyid AND LEFT(r01.caseid, -3) = h0.hhid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        GROUP BY r01.surveyid, r01.caseid, r01.v001, r01.v024, clust.latnum, clust.longnum, h0.hv025, r11.v190
        ORDER BY r01.surveyid::Integer, r01.v024::Integer, r01.v001::Integer, r01.caseid
      SET_TO _clustQuery = SELECT
        r01.v001 as clusterid
        , r01.v024 as region
        , clust.latnum as latitude
        , clust.longnum as longitude
        , h0.hv025 as urban_rural
        , sum(1) as young_child
        , sum(r01.v005::Float / 1000000) as young_child_wt
        , sum(had_fever) had_fever
        , sum(case when had_fever=1 THEN r01.v005::Float / 1000000 ELSE 0 END) as had_fever_wt
        , sum(any_treat) any_treat
        , sum(case when any_treat=1 THEN r01.v005::Float / 1000000 ELSE 0 END) as any_treat_wt
        , sum(public_treat) public_treat
        , sum(case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
        dhs_data_tables."RECH0" h0
        	-- dirty, but this is how it works
        	ON r01.surveyid = h0.surveyid AND LEFT(r01.caseid, -3) = h0.hhid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        GROUP BY r01.surveyid, r01.v001, r01.v024, clust.latnum, clust.longnum, h0.hv025
        ORDER BY r01.surveyid::Integer, r01.v024::Integer, r01.v001::Integer
      SET_TO _regionQuery = SELECT
        r01.v024 as region
        , sum(1) as young_child
        , sum(r01.v005::Float / 1000000) as young_child_wt
        , sum(had_fever) had_fever
        , sum(case when had_fever=1 THEN r01.v005::Float / 1000000 ELSE 0 END) as had_fever_wt
        , sum(any_treat) any_treat
        , sum(case when any_treat=1 THEN r01.v005::Float / 1000000 ELSE 0 END) as any_treat_wt
        , sum(public_treat) public_treat
        , sum(case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        GROUP BY r01.surveyid, r01.v024
        ORDER BY r01.surveyid::Integer, r01.v024::Integer
      SET_TO _nationalQuery = SELECT
        sum(1) as young_child
        , sum(r01.v005::Float / 1000000) as young_child_wt
        , sum(had_fever) had_fever
        , sum(case when had_fever=1 THEN r01.v005::Float / 1000000 ELSE 0 END) as had_fever_wt
        , sum(any_treat) any_treat
        , sum(case when any_treat=1 THEN r01.v005::Float / 1000000 ELSE 0 END) as any_treat_wt
        , sum(public_treat) public_treat
        , sum(case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        GROUP BY r01.surveyid
        ORDER BY r01.surveyid::Integer
    -> AttributeKeeper_3
AttributeKeeper_3
    KEEP_ATTRS = _clustQuery,_childQuery,_nationalQuery,_regionQuery,surveyid,_wmnQuery
    -> SQLExecutor_WMN [INITIATOR]
    -> QueryInitiators
    -> SQLExecutor_CLST [INITIATOR]
    -> SQLExecutor_RGN [INITIATOR]
    -> SQLExecutor_NTL [INITIATOR]
    -> SQLExecutor_CHILD [INITIATOR]
    -> AttributeManager_10
    -> AttributeManager_12
    -> AttributeManager_13
    -> AttributeManager_14
    -> AttributeManager_15
QueryInitiators: Inspector [off]

Bookmark: Run queries
SQLExecutor_WMN
    COMBINE_ATTRS = Keep Result Attributes if Conflict
    COMBINE_GEOM = Initiator Geometry Only
    DATASET = DHS Data Readonly
    EXPOSED_ATTRIBUTE_LIST = any_treat,any_treat_wt,clusterid,urban_rural,wealth_quint,had_fever,had_fever_wt,latitude,longitude,public_treat,public_treat_wt,region,survey_id,woman_id,young_child,young_child_wt
    FORMAT = POSTGRES
    POSTGRES_NAMED_CONNECTION = DHS Data Readonly
    POSTGRES_QUERY_FEATURE_TYPES_FOR_MERGE_FILTERS = Yes
    SQL_STATEMENT = @Value(_wmnQuery)
    RESULT -> AttributeManager
    <REJECTED> -> LOG_Rejected_SQL
SQLExecutor_RGN
    COMBINE_ATTRS = Keep Result Attributes if Conflict
    COMBINE_GEOM = Initiator Geometry Only
    DATASET = DHS Data Readonly
    EXPOSED_ATTRIBUTE_LIST = any_treat,any_treat_wt,had_fever,had_fever_wt,public_treat,public_treat_wt,region,survey_id,young_child,young_child_wt
    FORMAT = POSTGRES
    POSTGRES_NAMED_CONNECTION = DHS Data Readonly
    POSTGRES_QUERY_FEATURE_TYPES_FOR_MERGE_FILTERS = Yes
    SQL_STATEMENT = @Value(_regionQuery)
    RESULT -> AttributeManager_3
    <REJECTED> -> LOG_Rejected_SQL
SQLExecutor_CLST
    COMBINE_ATTRS = Keep Result Attributes if Conflict
    COMBINE_GEOM = Initiator Geometry Only
    DATASET = DHS Data Readonly
    EXPOSED_ATTRIBUTE_LIST = any_treat,any_treat_wt,clusterid,urban_rural,had_fever,had_fever_wt,latitude,longitude,public_treat,public_treat_wt,region,survey_id,young_child,young_child_wt
    FORMAT = POSTGRES
    POSTGRES_NAMED_CONNECTION = DHS Data Readonly
    POSTGRES_QUERY_FEATURE_TYPES_FOR_MERGE_FILTERS = Yes
    SQL_STATEMENT = @Value(_clustQuery)
    RESULT -> AttributeManager_2
    <REJECTED> -> LOG_Rejected_SQL
SQLExecutor_NTL
    COMBINE_ATTRS = Keep Result Attributes if Conflict
    COMBINE_GEOM = Initiator Geometry Only
    DATASET = DHS Data Readonly
    EXPOSED_ATTRIBUTE_LIST = any_treat,any_treat_wt,had_fever,had_fever_wt,public_treat,public_treat_wt,survey_id,young_child,young_child_wt
    FORMAT = POSTGRES
    POSTGRES_NAMED_CONNECTION = DHS Data Readonly
    POSTGRES_QUERY_FEATURE_TYPES_FOR_MERGE_FILTERS = Yes
    SQL_STATEMENT = @Value(_nationalQuery)
    RESULT -> AttributeManager_4
    <REJECTED> -> LOG_Rejected_SQL
SQLExecutor_CHILD
    COMBINE_ATTRS = Keep Result Attributes if Conflict
    COMBINE_GEOM = Initiator Geometry Only
    DATASET = DHS Data Readonly
    EXPOSED_ATTRIBUTE_LIST = any_treat,any_treat_wt,child_num,clusterid,urban_rural,wealth_quint,had_fever,had_fever_wt,latitude,longitude,public_treat,public_treat_wt,region,survey_id,woman_id,young_child,young_child_wt
    FORMAT = POSTGRES
    POSTGRES_NAMED_CONNECTION = DHS Data Readonly
    POSTGRES_QUERY_FEATURE_TYPES_FOR_MERGE_FILTERS = Yes
    SQL_STATEMENT = @Value(_childQuery)
    RESULT -> AttributeManager_CHILD
    RESULT -> StatisticsCalculator_WMN [off]
    RESULT -> StatisticsCalculator_CLUST [off]
    RESULT -> StatisticsCalculator_RGN [off]
    RESULT -> StatisticsCalculator_NTL [off]
    RESULT -> AttributeManager_CHILD_2
    RESULT -> AttributeManager_CHILD_3
    <REJECTED> -> LOG_Rejected_SQL
LOG_Rejected_SQL: Logger
    MAXCOORDS = 20
    MAXFEATS = 2000
    MESSAGE = Rejected SQL feature:

Bookmark: Calculate proportions
Note: Woman-level
AttributeManager
    ATTR_TABLE:
      REMOVE _childQuery
      REMOVE _wmnQuery
      REMOVE _clustQuery
      REMOVE _regionQuery
      REMOVE _nationalQuery
      RENAME_SET_VALUE young_child_wt > young_child_wt.wmncount
      RENAME_SET_VALUE had_fever_wt > had_fever_wt.wmncount
      RENAME_SET_VALUE public_treat_wt > public_treat_wt.wmncount
      RENAME_SET_VALUE any_treat_wt > any_treat_wt.wmncount
      SET_TO had_fever_wt.wmnprop = FME_CONDITIONAL:DEFAULT_VALUE'@Evaluate(@Value(had_fever_wt.wmncount)/@Value(young_child_wt.wmncount))'BOOL_OP;OR;COMPOSITE_TEST;<Unused>;TEST @Value(had_fever_wt.wmncount) = 0;TEST @Value(young_child_wt.wmncount) = 0'0'FME_NUM_CONDITIONS2___
      SET_TO fever_any_treat_wt.wmnprop = FME_CONDITIONAL:DEFAULT_VALUE'@Evaluate(@Value(any_treat_wt.wmncount)/@Value(had_fever_wt.wmncount))'BOOL_OP;OR;COMPOSITE_TEST;<Unused>;TEST @Value(had_fever_wt.wmncount) = 0;TEST @Value(any_treat_wt.wmncount) = 0'0'FME_NUM_CONDITIONS2___
      SET_TO fever_public_treat_wt.wmnprop = FME_CONDITIONAL:DEFAULT_VALUE'@Evaluate(@Value(public_treat_wt.wmncount)/@Value(had_fever_wt.wmncount))'BOOL_OP;OR;COMPOSITE_TEST;<Unused>;TEST @Value(had_fever_wt.wmncount) = 0;TEST @Value(public_treat_wt.wmncount) = 0'0'FME_NUM_CONDITIONS2___
    -> FeatureMerger_4 [REQUESTOR]
Note: Regional-level
AttributeManager_3
    ATTR_TABLE:
      REMOVE _childQuery
      REMOVE _wmnQuery
      REMOVE _clustQuery
      REMOVE _regionQuery
      REMOVE _nationalQuery
      RENAME_SET_VALUE any_treat_wt > any_treat_wt.regioncount
      RENAME_SET_VALUE had_fever_wt > had_fever_wt.regioncount
      RENAME_SET_VALUE public_treat_wt > public_treat_wt.regioncount
      RENAME_SET_VALUE young_child_wt > young_child_wt.regioncount
      SET_TO had_fever_wt.regionprop = @Evaluate(@Value(had_fever_wt.regioncount)/@Value(young_child_wt.regioncount))
      SET_TO fever_any_treat_wt.regionprop = @Evaluate(@Value(any_treat_wt.regioncount)/@Value(had_fever_wt.regioncount))
      SET_TO fever_public_treat_wt.regionprop = @Evaluate(@Value(public_treat_wt.regioncount)/@Value(had_fever_wt.regioncount))
    -> FeatureMerger_10 [REQUESTOR]
Note: Cluster-level / This contains unweighted vals too as of 20190528
AttributeManager_2
    ATTR_TABLE:
      REMOVE _childQuery
      REMOVE _wmnQuery
      REMOVE _clustQuery
      REMOVE _regionQuery
      REMOVE _nationalQuery
      RENAME_SET_VALUE any_treat_wt > any_treat_wt.clustcount
      RENAME_SET_VALUE had_fever_wt > had_fever_wt.clustcount
      RENAME_SET_VALUE public_treat_wt > public_treat_wt.clustcount
      RENAME_SET_VALUE young_child_wt > young_child_wt.clustcount
      SET_TO had_fever_wt.clustprop = FME_CONDITIONAL:DEFAULT_VALUE'@Evaluate(@Value(had_fever_wt.clustcount)/@Value(young_child_wt.clustcount))'BOOL_OP;OR;COMPOSITE_TEST;<Unused>;TEST @Value(young_child_wt.clustcount) = 0;TEST @Value(had_fever_wt.clustcount) = 0'0'FME_NUM_CONDITIONS2___
      SET_TO fever_any_treat_wt.clustprop = FME_CONDITIONAL:DEFAULT_VALUE'@Evaluate(@Value(any_treat_wt.clustcount)/@Value(had_fever_wt.clustcount))'BOOL_OP;OR;COMPOSITE_TEST;<Unused>;TEST @Value(any_treat_wt.clustcount) = 0;TEST @Value(had_fever_wt.clustcount) = 0'0'FME_NUM_CONDITIONS2___
      SET_TO fever_public_treat_wt.clustprop = FME_CONDITIONAL:DEFAULT_VALUE'@Evaluate(@Value(public_treat_wt.clustcount)/@Value(had_fever_wt.clustcount))'BOOL_OP;OR;COMPOSITE_TEST;<Unused>;TEST @Value(had_fever_wt.clustcount) = 0;TEST @Value(public_treat_wt.clustcount) = 0'0'FME_NUM_CONDITIONS2___
      RENAME_SET_VALUE any_treat > any_treat.clustcount
      RENAME_SET_VALUE had_fever > had_fever.clustcount
      RENAME_SET_VALUE public_treat > public_treat.clustcount
      RENAME_SET_VALUE young_child > young_child.clustcount
      SET_TO had_fever.clustprop = FME_CONDITIONAL:DEFAULT_VALUE'@Evaluate(@Value(had_fever.clustcount)/@Value(young_child.clustcount))'BOOL_OP;OR;COMPOSITE_TEST;<Unused>;TEST @Value(young_child.clustcount) = 0;TEST @Value(had_fever.clustcount) = 0'0'FME_NUM_CONDITIONS2___
      SET_TO fever_any_treat.clustprop = FME_CONDITIONAL:DEFAULT_VALUE'@Evaluate(@Value(any_treat.clustcount)/@Value(had_fever.clustcount))'BOOL_OP;OR;COMPOSITE_TEST;<Unused>;TEST @Value(any_treat.clustcount) = 0;TEST @Value(had_fever.clustcount) = 0'0'FME_NUM_CONDITIONS2___
      SET_TO fever_public_treat.clustprop = FME_CONDITIONAL:DEFAULT_VALUE'@Evaluate(@Value(public_treat.clustcount)/@Value(had_fever.clustcount))'BOOL_OP;OR;COMPOSITE_TEST;<Unused>;TEST @Value(had_fever.clustcount) = 0;TEST @Value(public_treat.clustcount) = 0'0'FME_NUM_CONDITIONS2___
    -> FeatureMerger_5 [REQUESTOR]
Note: national_level
AttributeManager_4
    ATTR_TABLE:
      REMOVE _childQuery
      REMOVE _wmnQuery
      REMOVE _clustQuery
      REMOVE _regionQuery
      REMOVE _nationalQuery
      RENAME_SET_VALUE any_treat_wt > any_treat_wt.nationalcount
      RENAME_SET_VALUE had_fever_wt > had_fever_wt.nationalcount
      RENAME_SET_VALUE public_treat_wt > public_treat_wt.nationalcount
      RENAME_SET_VALUE young_child_wt > young_child_wt.nationalcount
      SET_TO had_fever_wt.nationalprop = @Evaluate(@Value(had_fever_wt.nationalcount)/@Value(young_child_wt.nationalcount))
      SET_TO fever_any_treat_wt.nationalprop = @Evaluate(@Value(any_treat_wt.nationalcount)/@Value(had_fever_wt.nationalcount))
      SET_TO fever_public_treat_wt.nationalprop = @Evaluate(@Value(public_treat_wt.nationalcount)/@Value(had_fever_wt.nationalcount))
    -> FeatureMerger_9 [REQUESTOR]

Bookmark: Write out the SQL for reference
AttributeManager_10
    ATTR_TABLE:
      RENAME_SET_VALUE _childQuery > _sqlOutput
      REMOVE _wmnQuery
      REMOVE _clustQuery
      REMOVE _regionQuery
      REMOVE _nationalQuery
      SET_TO _sqlFN = @Value(surveyid).FST.ChildQuery.sql
    -> AttributeManager_16
AttributeManager_12
    ATTR_TABLE:
      REMOVE _childQuery
      RENAME_SET_VALUE _wmnQuery > _sqlOutput
      REMOVE _clustQuery
      REMOVE _regionQuery
      REMOVE _nationalQuery
      SET_TO _sqlFN = @Value(surveyid).FST.WomenQuery.sql
    -> AttributeManager_16
AttributeManager_13
    ATTR_TABLE:
      REMOVE _childQuery
      REMOVE _wmnQuery
      RENAME_SET_VALUE _clustQuery > _sqlOutput
      REMOVE _regionQuery
      REMOVE _nationalQuery
      SET_TO _sqlFN = @Value(surveyid).FST.ClustQuery.sql
    -> AttributeManager_16
AttributeManager_14
    ATTR_TABLE:
      REMOVE _childQuery
      REMOVE _wmnQuery
      REMOVE _clustQuery
      RENAME_SET_VALUE _regionQuery > _sqlOutput
      REMOVE _nationalQuery
      SET_TO _sqlFN = @Value(surveyid).FST.RegionQuery.sql
    -> AttributeManager_16
AttributeManager_15
    ATTR_TABLE:
      REMOVE _childQuery
      REMOVE _wmnQuery
      REMOVE _clustQuery
      REMOVE _regionQuery
      RENAME_SET_VALUE _nationalQuery > _sqlOutput
      SET_TO _sqlFN = @Value(surveyid).FST.NationalQuery.sql
    -> AttributeManager_16
Note: text file writer is surprisingly not your friend for this
AttributeManager_16
    ATTR_TABLE = SET_TO _sqlPath = $(IntermediateOutputFolder)\@Value(_sqlFN)
    -> AttributeFileWriter
AttributeFileWriter
    CHAR_ENCODING = fme-system
    FILE_NAME = @Value(_sqlPath)
    OVERWRITE_FILE = Overwrite file
    SOURCE_ATTR = _sqlOutput

Bookmark: Estimate regional CIs from child data
Note: Specifically for India - also do CIs for the regional data. A bit experimental and last minute! Unsure whether or not this is statistically valid.... but, also unsure whose pig that is
AttributeManager_CHILD_3
    ATTR_TABLE:
      REMOVE _childQuery
      REMOVE _wmnQuery
      REMOVE _clustQuery
      REMOVE _regionQuery
      REMOVE _nationalQuery
      REMOVE child_num
      REMOVE woman_id
      REMOVE clusterid
      REMOVE latitude
      REMOVE longitude
      SET_TO survey_and_region = @Value(surveyid)|@Value(region)
      REMOVE region
      REMOVE had_fever_wt
      REMOVE any_treat_wt
      REMOVE public_treat_wt
      REMOVE survey_id
      REMOVE young_child
      REMOVE urban_rural
      REMOVE wealth_quint
    -> Tester_10
Tester_10
    BOOL_OP = OR
    TEST_CLAUSE = TEST @Value(had_fever) > 0
    PASSED -> RCaller_4 [childraw]
RCaller_4
    OUTPUT_SCHEMA = survey_and_region svy_lci_public svy_uci_public svy_lci_any svy_uci_any
    QUERY_DEF:
      Output,library(plyr)
      # these next two libraries are required for running copies of the function (one per survey) in parallel
      # on windows - there are other choices than doParallel esp on linux
      library(foreach)
      library(doParallel)

      # function to create 95% confidence intervals for the national proportions based on the raw
      # child level had-treatment data. Input data should contain only children who had fever.
      createCIs <- function(dfInput){
        library(survey)

        dfOut <- tryCatch({

            # create a survey design object to use the survey package for estimating CIs
            SVY <- svydesign(id=~1, weights=~young_child_wt, data=dfInput)
            coefpub <- svymean(~public_treat, SVY, deff=FALSE, na.rm=TRUE)
            coefany <- svymean(~any_treat, SVY, deff=FALSE, na.rm=TRUE)
            svyconfpub <- confint(coefpub)
            svyconfany <- confint(coefany)

            data.frame(svy_lci_public=svyconfpub[1], svy_uci_public=svyconfpub[2],
              svy_lci_any=svyconfany[1], svy_uci_any=svyconfany[2])
        },
        error=function(cond){
            return (NULL)
        },
        warning=function(cond){return(NULL)}
        )
        return (dfOut)
      }

      # how many cores to use - my machine has 12, adjust to suit
      workers <- makeCluster(10)
      registerDoParallel(workers)

      # output a dataframe containing one row (=fme feature) for each input survey, by calling the
      # createCIs function for each survey's data in turn (like GROUP BY)
      # Use parallel functionality to ensure it runs in a decent amount of time. On a single core
      # with all 200+ surveys it takes 10 minutes+ and this times out in FME making the translation fail.
      fmeOutput <- ddply(childraw, "survey_and_region", createCIs, .parallel = TRUE)
      ,survey_and_region svy_lci_public svy_uci_public svy_lci_any svy_uci_any
    TABLE_DEF = childraw,surveyid,text,survey_and_region,text,any_treat,integer,had_fever,integer,young_child_wt,"real(20,10)",public_treat,integer
    -> AttributeSplitter
AttributeSplitter
    ATTR_NAME = survey_and_region
    DELIMITER = |
    DROP_EMPTY_PARTS = No
    LIST_NAME = _list
    TRIM_OPTION = Both
    -> ListIndexer
ListIndexer
    INDEX = 0
    LIST_ATTR = _list{}
    PREFIX = sid
    -> ListIndexer_2
ListIndexer_2
    INDEX = 1
    LIST_ATTR = _list{}
    PREFIX = rid
    -> AttributeManager_17
AttributeManager_17
    ATTR_TABLE:
      REMOVE _list{}
      RENAME_SET_VALUE sid_list > surveyid
      RENAME_SET_VALUE rid_list > region
    -> FeatureMerger_10 [SUPPLIER]
FeatureMerger_10
    ATTR_ACCUM_MODE = Merge Supplier
    ATTR_CONFLICT_RES = Use Requestor
    CLEANING_TOLERANCE = None
    IGNORE_NULLS = No
    JOIN_KEYS = @Value(surveyid) @Value(surveyid) AUTO @Value(region) @Value(region) AUTO
    MERGE_TYPE = Attributes Only
    PROCESS_DUPS = No
    REJECT_NULL_MISSING_KEYS = No
    SUPPLIERS_FIRST = No
    MERGED -> FeatureMerger_6 [REQUESTOR]

Bookmark: Summarise the results
Note: We could avoid hitting the database so much by just running the child-level query and then summarising the results here in FME using these statistics calculators. However I could only get 1 or 2 at once to respect the group ordering and spit out the features on the fly. The rest held on to them until the end, resulting in catastrophic slowness and memory usage. These statistic calculators are just left in for reference.
StatisticsCalculator_WMN [off]
    COMPUTE_HISTOGRAM = NO
    GROUP_BY = latitude region woman_id surveyid longitude clusterid
    PREPEND_ATTR_NAME_CHOICE = For all results
    STATS_ATTRS = public_treat_wt any_treat_wt had_fever_wt young_child_wt
    SUM_ATTR = wmncount
    SUMMARY -> woman [off]
woman: Inspector [off]
StatisticsCalculator_CLUST [off]
    COMPUTE_HISTOGRAM = NO
    GROUP_BY = latitude region surveyid longitude clusterid
    PREPEND_ATTR_NAME_CHOICE = For all results
    STATS_ATTRS = public_treat_wt any_treat_wt had_fever_wt young_child_wt
    SUM_ATTR = clustcount
    SUMMARY -> cluster [off]
cluster: Inspector [off]
StatisticsCalculator_RGN [off]
    COMPUTE_HISTOGRAM = NO
    GROUP_BY = region surveyid
    PREPEND_ATTR_NAME_CHOICE = For all results
    STATS_ATTRS = public_treat_wt any_treat_wt had_fever_wt young_child_wt
    SUM_ATTR = regioncount
    SUMMARY -> region [off]
region: Inspector [off]
StatisticsCalculator_NTL [off]
    COMPUTE_HISTOGRAM = NO
    GROUP_BY = surveyid
    PREPEND_ATTR_NAME_CHOICE = For all results
    STATS_ATTRS = public_treat_wt any_treat_wt had_fever_wt young_child_wt
    SUM_ATTR = nationalcount
    SUMMARY -> national [off]
national: Inspector [off]

Bookmark: Estimate CIs: FIX2 from child data
Note: This is the "correct" way of estimating CIs for the national estimates as it uses the data from which the national estimates are derived, i.e. the child data as opposed to cluster summaries
AttributeManager_CHILD_2
    ATTR_TABLE:
      REMOVE _childQuery
      REMOVE _wmnQuery
      REMOVE _clustQuery
      REMOVE _regionQuery
      REMOVE _nationalQuery
      REMOVE child_num
      REMOVE woman_id
      REMOVE clusterid
      REMOVE latitude
      REMOVE longitude
      REMOVE region
      REMOVE had_fever_wt
      REMOVE any_treat_wt
      REMOVE public_treat_wt
      REMOVE survey_id
      REMOVE young_child
      REMOVE urban_rural
      REMOVE wealth_quint
    -> Tester_9
Tester_9
    BOOL_OP = OR
    TEST_CLAUSE = TEST @Value(had_fever) > 0
    PASSED -> RCaller_3 [childraw]
RCaller_3
    OUTPUT_SCHEMA = surveyid svy_lci_public svy_uci_public svy_lci_any svy_uci_any
    QUERY_DEF:
      Output,library(plyr)
      # these next two libraries are required for running copies of the function (one per survey) in parallel
      # on windows - there are other choices than doParallel esp on linux
      library(foreach)
      library(doParallel)

      # function to create 95% confidence intervals for the national proportions based on the raw
      # child level had-treatment data. Input data should contain only children who had fever.
      createCIs <- function(dfInput){
        library(survey)

        dfOut <- tryCatch({

            # create a survey design object to use the survey package for estimating CIs
            SVY <- svydesign(id=~1, weights=~young_child_wt, data=dfInput)
            coefpub <- svymean(~public_treat, SVY, deff=FALSE, na.rm=TRUE)
            coefany <- svymean(~any_treat, SVY, deff=FALSE, na.rm=TRUE)
            svyconfpub <- confint(coefpub)
            svyconfany <- confint(coefany)

            data.frame(svy_lci_public=svyconfpub[1], svy_uci_public=svyconfpub[2],
              svy_lci_any=svyconfany[1], svy_uci_any=svyconfany[2])
        },
        error=function(cond){
            return (NULL)
        },
        warning=function(cond){return(NULL)}
        )
        return (dfOut)
      }

      # how many cores to use - my machine has 12, adjust to suit
      workers <- makeCluster(10)
      registerDoParallel(workers)

      # output a dataframe containing one row (=fme feature) for each input survey, by calling the
      # createCIs function for each survey's data in turn (like GROUP BY)
      # Use parallel functionality to ensure it runs in a decent amount of time. On a single core
      # with all 200+ surveys it takes 10 minutes+ and this times out in FME making the translation fail.
      fmeOutput <- ddply(childraw, "surveyid", createCIs, .parallel = TRUE)
      ,surveyid svy_lci_public svy_uci_public svy_lci_any svy_uci_any
    TABLE_DEF = childraw,surveyid,text,any_treat,integer,had_fever,integer,young_child_wt,"real(20,10)",public_treat,integer
    -> FeatureMerger_9 [SUPPLIER]

Bookmark: Attach CIs to national figures
FeatureMerger_9
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(surveyid) @Value(surveyid) AUTO
    MERGE_TYPE = Attributes Only
    PROCESS_DUPS = Yes
    REJECT_NULL_MISSING_KEYS = No
    SUPPLIERS_FIRST = No
    MERGED -> AttributeManager_18
AttributeManager_18
    -> FeatureMerger_7 [REQUESTOR]

Bookmark: Format and save the outputs
CSV (reader CSV2_1)
    attributes: SurveyId string, DHS_CountryCode string, SurveyYear string, SurveyType string, SurveyStatus string, CountryName string, SurveyYearLabel string, SurveyNum string, IndicatorData string, RegionName string, SubregionName string, PublicationDate string, ReleaseDate string, SurveyCharacteristicIds string, Footnotes string, FieldworkStart string, FieldworkEnd string, ImplementingOrg string, NumberOfSamplePoints string, NumberofHouseholds string, UniverseOfWomen string, NumberOfWomen string, MinAgeWomen string, MaxAgeWomen string, UniverseOfMen string, NumberOfMen string, MinAgeMen string, MaxAgeMen string, NumberOfFacilities string
    -> AttributeManager_5
Note: Read survey info from API and format to attach
AttributeManager_5
    ATTR_TABLE:
      RENAME_SET_VALUE SurveyId > SurveyName
      RENAME_SET_VALUE SurveyNum > SurveyId
    -> FeatureMerger_4 [SUPPLIER]
    -> FeatureMerger_5 [SUPPLIER]
    -> FeatureMerger_6 [SUPPLIER]
    -> FeatureMerger_7 [SUPPLIER]
    -> FeatureMerger_8 [SUPPLIER]
FeatureMerger_4
    ATTR_ACCUM_MODE = Merge Supplier
    ATTR_CONFLICT_RES = Use Requestor
    CLEANING_TOLERANCE = None
    IGNORE_NULLS = No
    JOIN_KEYS = @Value(surveyid) @Value(SurveyId) AUTO
    MERGE_TYPE = Attributes Only
    PROCESS_DUPS = No
    REJECT_NULL_MISSING_KEYS = No
    SUPPLIERS_FIRST = Yes
    MERGED -> AttributeManager_6
    UNMERGED_REQUESTOR -> AttributeManager_6
AttributeManager_6
    ATTR_TABLE:
      REMOVE SurveyId
      RENAME_SET_VALUE surveyid > SurveyId
      SET_TO _OutFN = FST_ByWoman_@Value(SurveyId)_@Value(SurveyName)
      SET_TO _OutFN_Single = FST_ByWoman_ALL
    -> File1 (writer CSV2_3)
    -> File101 (writer CSV2_3)
File1 (writer CSV2_3)
    attributes: SurveyName string, SurveyId string, DHS_CountryCode string, SurveyYear string, SurveyType string, SurveyStatus string, CountryName string, SurveyYearLabel string, woman_id string, clusterid string, latitude string, longitude string, region string, urban_rural string, wealth_quint string, young_child_wt.wmncount string, had_fever_wt.wmncount string, public_treat_wt.wmncount string, any_treat_wt.wmncount string, had_fever_wt.wmnprop string, fever_public_treat_wt.wmnprop string, fever_any_treat_wt.wmnprop string
File101 (writer CSV2_3)
    attributes: SurveyName string, SurveyId string, DHS_CountryCode string, SurveyYear string, SurveyType string, SurveyStatus string, CountryName string, SurveyYearLabel string, woman_id string, clusterid string, latitude string, longitude string, region string, urban_rural string, wealth_quint string, young_child_wt.wmncount string, had_fever_wt.wmncount string, public_treat_wt.wmncount string, any_treat_wt.wmncount string, had_fever_wt.wmnprop string, fever_public_treat_wt.wmnprop string, fever_any_treat_wt.wmnprop string
FeatureMerger_6
    ATTR_ACCUM_MODE = Merge Supplier
    ATTR_CONFLICT_RES = Use Requestor
    CLEANING_TOLERANCE = None
    IGNORE_NULLS = No
    JOIN_KEYS = @Value(surveyid) @Value(SurveyId) AUTO
    MERGE_TYPE = Attributes Only
    PROCESS_DUPS = No
    REJECT_NULL_MISSING_KEYS = No
    SUPPLIERS_FIRST = Yes
    MERGED -> AttributeManager_8
    UNMERGED_REQUESTOR -> AttributeManager_8
AttributeManager_8
    ATTR_TABLE:
      REMOVE SurveyId
      RENAME_SET_VALUE surveyid > SurveyId
      RENAME_SET_VALUE svy_lci_public > fever_public_treat_wt.regionprop_LCI_SVY
      RENAME_SET_VALUE svy_uci_public > fever_public_treat_wt.regionprop_UCI_SVY
      RENAME_SET_VALUE svy_lci_any > fever_any_treat_wt.regionprop_LCI_SVY
      RENAME_SET_VALUE svy_uci_any > fever_any_treat_wt.regionprop_UCI_SVY
      SET_TO _OutFN = FST_ByRegion_@Value(SurveyId)_@Value(SurveyName)
      SET_TO _OutFN_Single = FST_ByRegion_ALL
    -> File10000 (writer CSV2_3)
    -> File1000001 (writer CSV2_3)
File10000 (writer CSV2_3)
    attributes: SurveyName string, SurveyId string, DHS_CountryCode string, SurveyYear string, SurveyType string, SurveyStatus string, CountryName string, SurveyYearLabel string, region string, young_child_wt.regioncount string, had_fever_wt.regioncount string, public_treat_wt.regioncount string, any_treat_wt.regioncount string, had_fever_wt.regionprop string, fever_public_treat_wt.regionprop string, fever_public_treat_wt.regionprop_LCI_SVY string, fever_public_treat_wt.regionprop_UCI_SVY string, fever_any_treat_wt.regionprop string, fever_any_treat_wt.regionprop_LCI_SVY string, fever_any_treat_wt.regionprop_UCI_SVY string
File1000001 (writer CSV2_3)
    attributes: SurveyName string, SurveyId string, DHS_CountryCode string, SurveyYear string, SurveyType string, SurveyStatus string, CountryName string, SurveyYearLabel string, region string, young_child_wt.regioncount string, had_fever_wt.regioncount string, public_treat_wt.regioncount string, any_treat_wt.regioncount string, had_fever_wt.regionprop string, fever_public_treat_wt.regionprop string, fever_public_treat_wt.regionprop_LCI_SVY string, fever_public_treat_wt.regionprop_UCI_SVY string, fever_any_treat_wt.regionprop string, fever_any_treat_wt.regionprop_LCI_SVY string, fever_any_treat_wt.regionprop_UCI_SVY string
FeatureMerger_5
    ATTR_ACCUM_MODE = Merge Supplier
    ATTR_CONFLICT_RES = Use Requestor
    CLEANING_TOLERANCE = None
    IGNORE_NULLS = No
    JOIN_KEYS = @Value(surveyid) @Value(SurveyId) AUTO
    MERGE_TYPE = Attributes Only
    PROCESS_DUPS = No
    REJECT_NULL_MISSING_KEYS = No
    SUPPLIERS_FIRST = Yes
    MERGED -> AttributeManager_7
    UNMERGED_REQUESTOR -> AttributeManager_7
AttributeManager_7
    ATTR_TABLE:
      REMOVE SurveyId
      RENAME_SET_VALUE surveyid > SurveyId
      SET_TO _OutFN = FST_ByCluster_@Value(SurveyId)_@Value(SurveyName)
      SET_TO _OutFN_Single = FST_ByCluster_ALL
    -> File100 (writer CSV2_3)
    -> File10001 (writer CSV2_3)
File100 (writer CSV2_3)
    attributes: SurveyName string, SurveyId string, DHS_CountryCode string, SurveyYear string, SurveyType string, SurveyStatus string, CountryName string, SurveyYearLabel string, clusterid string, latitude string, longitude string, region string, urban_rural string, young_child_wt.clustcount string, had_fever_wt.clustcount string, public_treat_wt.clustcount string, any_treat_wt.clustcount string, had_fever_wt.clustprop string, fever_public_treat_wt.clustprop string, fever_any_treat_wt.clustprop string, young_child.clustcount string, had_fever.clustcount string, public_treat.clustcount string, any_treat.clustcount string, had_fever.clustprop string, fever_public_treat.clustprop string, fever_any_treat.clustprop string
File10001 (writer CSV2_3)
    attributes: SurveyName string, SurveyId string, DHS_CountryCode string, SurveyYear string, SurveyType string, SurveyStatus string, CountryName string, SurveyYearLabel string, clusterid string, latitude string, longitude string, region string, urban_rural string, young_child_wt.clustcount string, had_fever_wt.clustcount string, public_treat_wt.clustcount string, any_treat_wt.clustcount string, had_fever_wt.clustprop string, fever_public_treat_wt.clustprop string, fever_any_treat_wt.clustprop string, young_child.clustcount string, had_fever.clustcount string, public_treat.clustcount string, any_treat.clustcount string, had_fever.clustprop string, fever_public_treat.clustprop string, fever_any_treat.clustprop string
FeatureMerger_8
    ATTR_ACCUM_MODE = Merge Supplier
    ATTR_CONFLICT_RES = Use Requestor
    CLEANING_TOLERANCE = None
    IGNORE_NULLS = No
    JOIN_KEYS = @Value(surveyid) @Value(SurveyId) AUTO
    MERGE_TYPE = Attributes Only
    PROCESS_DUPS = No
    REJECT_NULL_MISSING_KEYS = No
    SUPPLIERS_FIRST = Yes
    MERGED -> AttributeManager_11
    UNMERGED_REQUESTOR -> AttributeManager_11
AttributeManager_11
    ATTR_TABLE:
      REMOVE SurveyId
      RENAME_SET_VALUE surveyid > SurveyId
      REMOVE survey_id
      REMOVE young_child
      SET_TO _OutFN = FST_ByChild_@Value(SurveyId)_@Value(SurveyName)
      SET_TO _OutFN_Single = FST_ByChild_ALL
    -> File100000000 (writer CSV2_3)
    -> File10000000000 (writer CSV2_3)
File100000000 (writer CSV2_3)
    attributes: SurveyName string, SurveyId string, DHS_CountryCode string, SurveyYear string, SurveyType string, SurveyStatus string, CountryName string, SurveyYearLabel string, child_num string, woman_id string, clusterid string, latitude string, longitude string, region string, urban_rural string, wealth_quint string, young_child_wt string, had_fever_wt string, public_treat_wt string, any_treat_wt string
File10000000000 (writer CSV2_3)
    attributes: SurveyName string, SurveyId string, DHS_CountryCode string, SurveyYear string, SurveyType string, SurveyStatus string, CountryName string, SurveyYearLabel string, child_num string, woman_id string, clusterid string, latitude string, longitude string, region string, urban_rural string, wealth_quint string, young_child_wt string, had_fever_wt string, public_treat_wt string, any_treat_wt string
FeatureMerger_7
    ATTR_ACCUM_MODE = Merge Supplier
    ATTR_CONFLICT_RES = Use Requestor
    CLEANING_TOLERANCE = None
    IGNORE_NULLS = No
    JOIN_KEYS = @Value(surveyid) @Value(SurveyId) AUTO
    MERGE_TYPE = Attributes Only
    PROCESS_DUPS = No
    REJECT_NULL_MISSING_KEYS = No
    SUPPLIERS_FIRST = Yes
    MERGED -> AttributeManager_9
    UNMERGED_REQUESTOR -> Missing_National_Svy_Info
    UNMERGED_REQUESTOR -> AttributeManager_9
AttributeManager_9
    ATTR_TABLE:
      REMOVE SurveyId
      RENAME_SET_VALUE surveyid > SurveyId
      SET_TO _OutFN = FST_BySurvey_@Value(SurveyId)_@Value(SurveyName)
      SET_TO _OutFN_Single = FST_BySurvey_ALL
      RENAME_SET_VALUE svy_lci_public > fever_public_treat_wt.nationalprop_LCI_SVY
      RENAME_SET_VALUE svy_uci_public > fever_public_treat_wt.nationalprop_UCI_SVY
      RENAME_SET_VALUE svy_lci_any > fever_any_treat_wt.nationalprop_LCI_SVY
      RENAME_SET_VALUE svy_uci_any > fever_any_treat_wt.nationalprop_UCI_SVY
    -> bob (writer CSV2_3)
    -> File100000001 (writer CSV2_3)
    -> natl_output_check_calcs
natl_output_check_calcs: Inspector [off]
File100000001 (writer CSV2_3)
    attributes: SurveyName string, SurveyId string, DHS_CountryCode string, SurveyYear string, SurveyType string, SurveyStatus string, CountryName string, SurveyYearLabel string, young_child_wt.nationalcount string, had_fever_wt.nationalcount string, public_treat_wt.nationalcount string, any_treat_wt.nationalcount string, had_fever_wt.nationalprop string, fever_public_treat_wt.nationalprop string, fever_any_treat_wt.nationalprop string, fever_public_treat_wt.nationalprop_LCI_SVY string, fever_public_treat_wt.nationalprop_UCI_SVY string, fever_any_treat_wt.nationalprop_LCI_SVY string, fever_any_treat_wt.nationalprop_UCI_SVY string
bob (writer CSV2_3)
    attributes: SurveyName string, SurveyId string, DHS_CountryCode string, SurveyYear string, SurveyType string, SurveyStatus string, CountryName string, SurveyYearLabel string, young_child_wt.nationalcount string, had_fever_wt.nationalcount string, public_treat_wt.nationalcount string, any_treat_wt.nationalcount string, had_fever_wt.nationalprop string, fever_public_treat_wt.nationalprop string, fever_any_treat_wt.nationalprop string, fever_public_treat_wt.nationalprop_LCI_SVY string, fever_public_treat_wt.nationalprop_UCI_SVY string, fever_any_treat_wt.nationalprop_LCI_SVY string, fever_any_treat_wt.nationalprop_UCI_SVY string
Missing_National_Svy_Info: Inspector

Bookmark: Estimate national CIs from child data
Note: Previously (in v1) confidence intervals for the national estimates were calculated by Kate. In v2 we have brought that calculation into the FME workflow. / We have also changed the methodology for calculating them as the old methodology was not suitable for the data. After several iterations and trials we are using the R "survey" package.
