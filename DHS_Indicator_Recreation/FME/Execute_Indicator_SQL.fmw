FME workspace Execute_Indicator_SQL.fmw

Parameters:
- SourceDataset_XLSXR = \\map-fs1.ndph.ox.ac.uk\map_data\DHS_Automation\Processing\DHS_Extractions_For_DHS\Extra_Surveys_201609\input\surveys_to_run.xlsx   # Source Microsoft Excel File(s)
- Indicator = AH_TOBC_M_NON
- TopOutFolder = \\map-fs1.ndph.ox.ac.uk\map_data\DHS_Automation\Processing\DHS_Extractions_For_DHS\Extra_Surveys_201609\output   # Top level output folder
- SQL_Folder = \\map-fs1.ndph.ox.ac.uk\map_data\DHS_Automation\Processing\DHS_Extractions_For_DHS\DHSmapping2016_Code\SQL   # Folder with SQL files each named with API indicator title
- DestDataset_CSV = \\map-fs1.ndph.ox.ac.uk\map_data\DHS_Automation\Processing\DHS_Extractions_For_DHS\Extra_Surveys_201609\output\Checks   # Destination CSV (Comma Separated Value) Folder
- Single_Survey_ID =   # (Re)run for a single survey?

Readers:
- XLSXR_1: XLSXR from $(SourceDataset_XLSXR)

Writers:
- CSV_1: CSV to $(TopOutFolder)
- CSV_2: CSV to $(DestDataset_CSV)

Country Details (reader XLSXR_1)
    attributes: Country char(11), Survey char(4), Year char(8), Release date, Notes char(40), Dataset_ID char(10), Svy_Num number(4,0)
    -> ParameterFetcher
Note: This worksheet on the spreadsheet was used to populate the Indicator parameter choice set. The indicator ref from here is used directly to build the API query URL, the name of the SQL file to look for, and the output folder names so typos matter....
Indicator-coding (reader XLSXR_1) [off]
    attributes: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
Note: Execute the SQL. The SQL for all indicators is written to have the same output column names: / clusterid, latititude, longitude, dhsid, urban_rural, denom_nonwt, denom_wt, num_nonwt, num_wt.
SQLExecutor
    COMBINE_ATTRS = Keep Result Attributes if Conflict
    DATASET = DHS Data Readonly
    SQL_STATEMENT = @Value(_SQL)
    POSTGRES_NAMED_CONNECTION = DHS Data Readonly
    POSTGRES_QUERY_FEATURE_TYPES_FOR_MERGE_FILTERS = Yes
    FORMAT = POSTGRES
    EXPOSED_ATTRIBUTE_LIST = clusterid,latitude,longitude,urban_rural,dhsid,denom_nonwt,denom_wt,num_nonwt,num_wt
    COMBINE_GEOM = Initiator Geometry Only
    RESULT -> BulkAttributeRenamer
    RESULT -> StatisticsCalculator
Note: Rename the numerator/denominator column by prepending the indicator ID. This means a dynamic schema is required, hence the working below.
BulkAttributeRenamer
    MODE_CHOICE = RENAME
    REPLACE_STR = @Value(_Prefix)
    PATTERN_ACTION_DISP = ADDPREFIX
    ATTRLIST = denom_wt num_wt denom_nonwt num_nonwt
    ATTRCHOICE = Selected Attributes
    -> File1 (writer CSV_1)
Note: Write the data using a dynamic filename, in addition to a fanout (on the writer properties) to also write to a dynamic folder, as required by His Peteliness
File1 (writer CSV_1)
StatisticsCalculator
    GROUP_BY = _Indicator Dataset_ID
    SUM_ATTR = _sum
    PREPEND_ATTR_NAME_CHOICE = For multiple results only
    COMPUTE_HISTOGRAM = NO
    STATS_ATTRS = denom_wt num_wt denom_nonwt
    SUMMARY -> AttributeManager_3
AttributeManager_3
    ATTR_TABLE:
      RENAME_SET_VALUE num_wt._sum > Calculated_Numerator_Weighted
      RENAME_SET_VALUE denom_wt._sum > Calculated_Denom_Weighted
      RENAME_SET_VALUE denom_nonwt._sum > Calculated_Denom_Unweighted
      SET_TO Calculated_Value = @Evaluate((@Value(Calculated_Numerator_Weighted)/@Value(Calculated_Denom_Weighted))*100)
      SET_TO Checks_OK = 1
      SET_TO _api_check_URL = http://api.dhsprogram.com/rest/dhs/data/@Value(_Indicator)?f=csv&surveyIds=@Value(Dataset_ID)
    -> FeatureReader [INITIATOR]
FeatureReader
    CSV__SCHEMA = number,7,0,char,31,,number,4,1,number,2,0,char,3,,char,9,,number,5,0,char,10,,char,14,,number,9,0,number,5,0,number,2,0,char,6,,char,6,,number,2,0,char,1,,number,2,0,number,2,0,number,5,0,char,1,,number,5,0,char,4,,number,6,0,number,6,0,char,1,,char,1,,number,2,0,number,2,0,number,2,0
    ATTR_ACCUM_MODE = Merge Initiator and Result
    CSV__SKIP_LINES = 1
    FORMAT = CSV
    CSV__IN_FIELD_NAMES = YES
    CSV__DUPLICATE_DELIMS = no
    OUTPUT_FEATURES_DISPLAY = Schema and Data Features
    CSV_SCAN_MAX_FEATURES = 1000
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES DataId%Indicator%Value%Precision%DHS_CountryCode%CountryName%SurveyYear%SurveyId%IndicatorId%IndicatorOrder%CharacteristicId%CharacteristicOrder%CharacteristicCategory%CharacteristicLabel%ByVariableId%ByVariableLabel%IsTotal%IsPreferred%SDRID%RegionId%SurveyYearLabel%SurveyType%DenominatorWeighted%DenominatorUnweighted%CILow%CIHigh%Recordcount%Page%TotalPages\"%%\"Filter\"%\"STRING_ENCODED _FILTER_REGEX \"%%\"Invert Filter\"%\"CHECKBOX _FILTER_UNMATCHED yes%no\"%no"
    CSV__IN_SEPARATOR = ,
    CSV__FIELD_NAMES_AFTER_HEADER = no
    CSV__SKIP_FOOTER = 0
    CSV__ALLOW_SPACES_IN_COLUMN_NAMES = yes
    CSV__GROUP_BY_DATASET = no
    ATTRS_TO_EXPOSE = DenominatorWeighted DenominatorUnweighted Value IsPreferred
    COMBINE_GEOM = Use Result
    ATTR_CONFLICT_RES = Use Result
    DATASET = @Value(_api_check_URL)
    CSV__STRIP_QUOTES = yes
    CSV__SCHEMA_WITH_COL_NAMES = DataId,number,7,0,Indicator,char,31,,Value,number,4,1,Precision,number,2,0,DHS_CountryCode,char,3,,CountryName,char,9,,SurveyYear,number,5,0,SurveyId,char,10,,IndicatorId,char,14,,IndicatorOrder,number,9,0,CharacteristicId,number,5,0,CharacteristicOrder,number,2,0,CharacteristicCategory,char,6,,CharacteristicLabel,char,6,,ByVariableId,number,2,0,ByVariableLabel,char,1,,IsTotal,number,2,0,IsPreferred,number,2,0,SDRID,number,5,0,RegionId,char,1,,SurveyYearLabel,number,5,0,SurveyType,char,4,,DenominatorWeighted,number,6,0,DenominatorUnweighted,number,6,0,CILow,char,1,,CIHigh,char,1,,Recordcount,number,2,0,Page,number,2,0,TotalPages,number,2,0
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES DataId%Indicator%Value%Precision%DHS_CountryCode%CountryName%SurveyYear%SurveyId%IndicatorId%IndicatorOrder%CharacteristicId%CharacteristicOrder%CharacteristicCategory%CharacteristicLabel%ByVariableId%ByVariableLabel%IsTotal%IsPreferred%SDRID%RegionId%SurveyYearLabel%SurveyType%DenominatorWeighted%DenominatorUnweighted%CILow%CIHigh%Recordcount%Page%TotalPages\"%%\"Alpha/Num\"%\"LOOKUP_CHOICE SORT_CHOICE Alphabetic,alphabetic%Numeric,numeric\"%alphabetic%\"Order\"%\"LOOKUP_CHOICE SORT_ORDER Ascending,ascending%Descending,descending\"%ascending"
    <OTHER> -> AttributeManager
    <REJECTED> -> AttributeManager_2
AttributeManager
    ATTR_TABLE:
      RENAME_SET_VALUE DenominatorWeighted > API_Denominator_Weighted
      RENAME_SET_VALUE DenominatorUnweighted > API_Denominator_Unweighted
      RENAME_SET_VALUE Value > API_Value
    -> Sorter_2
Note: sometimes the API returns two rows for a single survey and indicator, with "IsPreferred" = 1 for one and not for the other. If there's only one row sent, than "IsPreferred" isn't necessarily 1! So get the preferred row if present or the only row otherwise.
Sorter_2
    SORT_PARM = Dataset_ID ALPHA ASCENDING IsPreferred NUMERIC DESCENDING
    SORTED -> Sampler
Sampler
    RATE = 1
    GROUP_BY = Dataset_ID
    SAMPLE_TYPE_LONG = First N Features
    SAMPLE_MODE = No
    SAMPLED -> Tester_4
Tester_4
    TEST_MODE = Automatic
    BOOL_OP = AND
    TEST_DESCRIPTION = ""
    TEST_CLAUSE:
      TEST @Evaluate(abs(1-(@Value(Calculated_Denom_Unweighted)/@Value(API_Denominator_Unweighted)))) <= 0.01
      TEST @Evaluate(abs(1-(@Value(Calculated_Denom_Weighted)/@Value(API_Denominator_Weighted)))) <= 0.01
      TEST @Evaluate(abs(1-(@Value(Calculated_Value)/@Value(API_Value)))) <= 0.01
    PASSED -> LooksOkToMe
    PASSED -> File1 (writer CSV_2)
    FAILED -> AttributeCreator_6
LooksOkToMe: Inspector
AttributeManager_2
    ATTR_TABLE:
      REMOVE _reader_error
      SET_TO API_Check_Unavailable = No Response From API - Cannot Check
    -> AttributeCreator_6
AttributeCreator_6
    ATTR_TABLE = SET_TO Checks_OK = 0
    -> File1 (writer CSV_2)
    -> WaWaOops
File1 (writer CSV_2)
    attributes: Dataset_ID char(10), Checks_OK auto, _api_check_URL auto, _Indicator auto, Calculated_Numerator_Weighted auto, Calculated_Denom_Weighted auto, Calculated_Denom_Unweighted auto, Calculated_Value auto, API_Denominator_Weighted auto, API_Denominator_Unweighted auto, API_Value auto, API_Check_Unavailable auto
WaWaOops: Inspector

Bookmark: Fetch and process params
Note: The indicator code parameter choices (descriptions and values) were configured by importing Clara's spreadsheet directly. / This indicator code is then used to define the output folder and also the name of the SQL file that will be read
ParameterFetcher
    ATTR_LIST = _Indicator {$(Indicator)} _TopOutFolder {$(TopOutFolder)} _SQL_Folder {$(SQL_Folder)} _Single_Survey_ID {$(Single_Survey_ID)}
    -> AttributeCreator
AttributeCreator
    ATTR_TABLE:
      SET_TO _OutFolder = @Value(_TopOutFolder)\@Value(Dataset_ID)\@Value(_Indicator)
      SET_TO _OutFN = @Value(Dataset_ID)_@Value(_Indicator)_Clusters
      SET_TO _SQLFile = @Value(_SQL_Folder)\@Value(_Indicator).sql
      SET_TO _Prefix = @Value(_Indicator)_
    -> Tester
Tester
    TEST_MODE = Automatic
    COMPOSITE_TEST = "1 AND (2 OR 3)"
    BOOL_OP = COMPOSITE
    TEST_DESCRIPTION = ""
    TEST_CLAUSE:
      TEST @Value(Svy_Num) CONTAINS_REGEX \d+
      TEST @Value(_Single_Survey_ID) NOT_ATTRIBUTE_HAS_VALUE ""
      TEST @Value(Svy_Num) = @Value(_Single_Survey_ID)
    PASSED -> AttributeFileReader

Bookmark: Read the generic SQL for this indicator and substitute in survey id
AttributeFileReader
    CHAR_ENCODING = utf-8
    DEST_ATTR = _SQL
    FILE_NAME = @Value(_SQLFile)
    -> StringReplacer
StringReplacer
    NO_MATCH = _FME_NO_OP_
    FIND_TEXT = {SURVEYID}
    SRC_ATTRS = _SQL
    REPLACE_TEXT = @Value(Svy_Num)
    REGEXP = NO
    CASE = NO
    -> FeatureMerger [REQUESTOR]
Note: Attach dynamic schema info
FeatureMerger
    IGNORE_NULLS = No
    MERGE_TYPE = Attributes Only
    SUPPLIERS_FIRST = No
    ATTR_CONFLICT_RES = Use Requestor
    JOIN_KEYS = 1 1 AUTO
    REJECT_NULL_MISSING_KEYS = No
    ATTR_ACCUM_MODE = Merge Supplier
    PROCESS_DUPS = No
    MERGED -> SQLExecutor [INITIATOR]
    MERGED -> Queries_To_Run
Queries_To_Run: Inspector

Bookmark: Generate output CSV dynamic column names
Creator
    GEOMTYPE = Geometry Object
    NUM = 1
    CREATED -> AttributeCreator_2
Note: Create all the attributes we want the output to have and prefix with a number so they can be sorted and appear in this order in the output CSV
AttributeCreator_2
    ATTR_TABLE:
      SET_TO 00_clusterid
      SET_TO 01_latitude
      SET_TO 02_longitude
      SET_TO 03_urban_rural
      SET_TO 04_dhsid
      SET_TO 05_denom_nonwt
      SET_TO 06_denom_wt
      SET_TO 07_num_nonwt
      SET_TO 08_num_wt
    -> AttributeExploder
AttributeExploder
    EXPLODING_TYPE = Features
    ATTR_NAME_LABEL = name
    KEEP_GEOMETRY = No
    ATTR_VALUE_LABEL = _blah
    KEEP_ATTRIBUTES = No
    -> AttributeCreator_3
AttributeCreator_3
    ATTR_TABLE = SET_TO fme_data_type = fme_buffer
    -> AttributeRemover
AttributeRemover
    REMOVE_ATTRS = _blah
    -> Tester_2
Tester_2
    TEST_MODE = Automatic
    BOOL_OP = OR
    TEST_DESCRIPTION = ""
    TEST_CLAUSE = TEST @Value(name) BEGINS_WITH fme_
    FAILED -> Sorter
Note: Sort them so the list, and thence the output columns, are in the required order
Sorter
    SORT_PARM = name ALPHA ASCENDING
    SORTED -> StringReplacer_2
Note: Remove the numeric sorting text
StringReplacer_2
    NO_MATCH = _FME_NO_OP_
    FIND_TEXT = ^\d+_
    SRC_ATTRS = name
    REGEXP = YES
    CASE = NO
    -> Tester_3
Note: Prepend the indicator ID to the result column names, but not to the standard cluster info column names
Tester_3
    TEST_MODE = Automatic
    BOOL_OP = OR
    TEST_DESCRIPTION = ""
    TEST_CLAUSE = TEST @Value(name) IN denom_nonwt,num_nonwt,denom_wt,num_wt
    PASSED -> AttributeCreator_4
    FAILED -> ListBuilder
AttributeCreator_4
    ATTR_TABLE = SET_TO name = $(Indicator)_@Value(name)
    -> ListBuilder
Note: Build the attribute{} list for the dynamic writer to use
ListBuilder
    LIST_NAME = attribute
    -> FeatureMerger [SUPPLIER]
