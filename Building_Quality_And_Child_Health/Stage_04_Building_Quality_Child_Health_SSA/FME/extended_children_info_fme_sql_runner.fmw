FME workspace extended_children_info_fme_sql_runner.fmw

Parameters:
- Children_Info_SQL = $(FME_MF_DIR_ENCODED)HH_Level_Children_Health_Generic_Query_2018.sql   # SQL file for the extraction
- DestDataset_CSV = C:\Users\zool1301.NDPH\Documents\DHS\Processing\child_health_20190403   # Destination CSV (Comma Separated Value) Folder

Readers:
- XLSXR_1: XLSXR from \\map-fs1.ndph.ox.ac.uk\map_data\DHS_Automation\SupportingInfo\Standard country codes.xlsx

Writers:
- CSV_1: CSV to $(DestDataset_CSV)

SQLExecutor_2
    COMBINE_ATTRS = Keep Result Attributes if Conflict
    COMBINE_GEOM = Initiator Geometry Only
    DATASET = DHS Data Readonly
    EXPOSED_ATTRIBUTE_LIST = b8_child_age,birth_order,child_hh_line_num,child_sex,cluster_id_full,countryname,desc_child_sex,dhs_countrycode,h1_desc_has_health_card,h1_has_health_card,h7_received_dpt3,h9_received_measles,h11_desc_had_diarrhea_recently,h11_had_diarrhea_recently,h22_had_fever_recently,h31_had_cough_recently,h31b_short_rapid_breaths,h31c_problem_in_chest,h34_had_vitamin_a,h56_received_pneumococcal,h58_received_rv2,hc5_ht_age_stdev,hc8_wt_age_stdev,hc11_wt_ht_stdev,hc56_hb_adj_alt,hc57_anemia_level,hc57_desc_anemia_level,hc61_desc_mother_highest_ed_lvl,hc61_mother_highest_ed_lvl,hc62_desc_mother_highest_ed_yr,hc62_mother_highest_ed_yr,hc70_ht_age_stdev_who,hc71_wt_age_stdev_who,hc72_wt_ht_stdev_who,hhid,hml_20_sleep_under_llin,hml12_desc_type_net_slept_last_night,hml12_type_net_slept_last_night,hml19_sleep_under_ever_treated_net,hml22_desc_had_fever_recently,hml31_desc_had_cough_recently,hml31b_desc_short_rapid_breaths,hml31c_desc_problem_in_chest,hml32_desc_result_mal_smear_test,hml32_result_mal_smear_test,hml33_desc_mal_smear_test_status,hml33_mal_smear_test_status,hml35_desc_result_mal_rapid_test,hml35_result_mal_rapid_test,hv000_ccode_phase,hv002_hh_num,hv006_interview_mth,hv007_interview_yr,hv008_child_age_cmc_calc_months,hv008_interview_cmc,hv105_child_age,latitude,longitude,m15_desc_place_of_delivery,m15_place_of_delivery,m17_delivery_by_csection,m19_birthweight_kg_3dec,m39_times_ate_stuff_yesterday,survey_release_date,surveynum,surveytype,surveyyear_lbl,v001_cluster_id,woman_caseid
    FORMAT = POSTGRES
    POSTGRES_NAMED_CONNECTION = DHS Data Readonly
    POSTGRES_QUERY_FEATURE_TYPES_FOR_MERGE_FILTERS = Yes
    POSTGRES_READ_TIME_WITH_TIMEZONE = Yes
    POSTGRES_SCHEMAS_FOR_TABLE_LISTING = dhs_data_tables
    SQL_STATEMENT = @Value(_SQL)
    RESULT -> AttributeManager
    <REJECTED> -> SQLExecutor_2__Rejected_
AttributeManager
    ATTR_TABLE:
      REMOVE _SQL
      REMOVE hv000
      REMOVE phase
      RENAME_SET_VALUE woman_caseid > mother_caseid
      REMOVE surveynum
    -> Children_All_20190403 (writer CSV_1)
Children_All_20190403 (writer CSV_1)
    attributes: surveyid auto, surveyyear auto, surveyyear_lbl auto, survey_release_date auto, surveytype auto, hv000_ccode_phase auto, dhs_countrycode auto, countryname auto, v001_cluster_id auto, cluster_id_full auto, latitude auto, longitude auto, hhid auto, hv002_hh_num auto, hv006_interview_mth auto, hv007_interview_yr auto, hv008_interview_cmc auto, child_hh_line_num auto, birth_order auto, child_sex auto, desc_child_sex auto, b8_child_age auto, hv105_child_age auto, hv008_child_age_cmc_calc_months auto, mother_caseid auto, hc61_mother_highest_ed_lvl auto, hc61_desc_mother_highest_ed_lvl auto, hc62_mother_highest_ed_yr auto, hc62_desc_mother_highest_ed_yr auto, h1_has_health_card auto,
      h1_desc_has_health_card auto, h11_had_diarrhea_recently auto, h11_desc_had_diarrhea_recently auto, h22_had_fever_recently auto, hml22_desc_had_fever_recently auto, h31_had_cough_recently auto, hml31_desc_had_cough_recently auto, h31b_short_rapid_breaths auto, hml31b_desc_short_rapid_breaths auto, h31c_problem_in_chest auto, hml31c_desc_problem_in_chest auto, h34_had_vitamin_a auto, h7_received_dpt3 auto, h56_received_pneumococcal auto, h58_received_rv2 auto, h9_received_measles auto, m15_place_of_delivery auto, m15_desc_place_of_delivery auto, m17_delivery_by_csection auto, m19_birthweight_kg_3dec auto, m39_times_ate_stuff_yesterday auto, hml12_desc_type_net_slept_last_night auto, hml12_type_net_slept_last_night auto, hml19_sleep_under_ever_treated_net auto, hml_20_sleep_under_llin auto, hml33_mal_smear_test_status auto, hml33_desc_mal_smear_test_status auto, hml32_result_mal_smear_test auto, hml32_desc_result_mal_smear_test auto, hml35_result_mal_rapid_test auto,
      hml35_desc_result_mal_rapid_test auto, hc70_ht_age_stdev_who auto, hc71_wt_age_stdev_who auto, hc72_wt_ht_stdev_who auto, hc5_ht_age_stdev auto, hc8_wt_age_stdev auto, hc11_wt_ht_stdev auto, hc56_hb_adj_alt auto, hc57_anemia_level auto, hc57_desc_anemia_level auto
SQLExecutor_2__Rejected_: Inspector
Note: Get listing of all sub-saharan surveys from the database, the table used here just contains a dump of the survey listing from the DHS API
StringReplacer_3_Output: Inspector [off]

Bookmark: Get Phase of all sub-saharan surveys in our DB
Note: HV000 is a combination of country code and phase
SQLCreator
    DATASET = DHS Data Readonly
    EXPOSED_ATTRIBUTE_LIST = hv000,surveyid
    FORMAT = POSTGRES
    POSTGRES_NAMED_CONNECTION = DHS Data Readonly
    POSTGRES_QUERY_FEATURE_TYPES_FOR_MERGE_FILTERS = Yes
    POSTGRES_SCHEMAS_FOR_TABLE_LISTING = dhs_data_locations dhs_data_tables
    SQL_STATEMENT = select distinct surveyid,hv000 from dhs_data_tables."RECH0"
    RESULT -> Tester
    RESULT -> FeatureMerger [REQUESTOR]
Tester [off]
    BOOL_OP = OR
    TEST_CLAUSE = TEST @Value(surveyid) = 253
FeatureMerger
    ATTR_ACCUM_MODE = Merge Supplier
    ATTR_CONFLICT_RES = Use Requestor
    IGNORE_NULLS = No
    JOIN_KEYS = @Value(surveyid) @Value(surveynum) AUTO
    MERGE_TYPE = Attributes Only
    PROCESS_DUPS = No
    REJECT_NULL_MISSING_KEYS = No
    SUPPLIERS_FIRST = No
    MERGED -> StringSearcher
StringSearcher
    CASE = no
    MATCHED_RESULT_ATTR = phase
    REGEXP = \d$
    STRING_TO_SEARCH = @Value(hv000)
    MATCHED -> AttributeValueMapper

Bookmark: Get listing of all sub-saharan surveys from the DHS API
SQLCreator_2
    DATASET = DHS Data Readonly
    EXPOSED_ATTRIBUTE_LIST = countryname,dhs_countrycode,publicationdate,regionname,releasedate,surveyid,surveynum,surveystatus,surveytype,surveyyear,surveyyearlabel
    FORMAT = POSTGRES
    POSTGRES_NAMED_CONNECTION = DHS Data Readonly
    POSTGRES_QUERY_FEATURE_TYPES_FOR_MERGE_FILTERS = Yes
    POSTGRES_READ_TIME_WITH_TIMEZONE = Yes
    POSTGRES_SCHEMAS_FOR_TABLE_LISTING = dhs_survey_specs
    SQL_STATEMENT = select * from "dhs_survey_specs"."dhs_survey_listing"
    RESULT -> Tester_2
Tester_2
    BOOL_OP = OR
    TEST_CLAUSE = TEST @Value(regionname) BEGINS_WITH Sub-Saharan
    PASSED -> AttributeKeeper_4
AttributeKeeper_4
    KEEP_ATTRS = countryname,surveytype,surveyyear,surveynum,dhs_countrycode
    -> FeatureMerger [SUPPLIER]

Bookmark: Load the appropriate SQL template for the survey phase
AttributeValueMapper
    DEFAULT_VALUE = $(Children_Info_SQL)
    DIRECTION = Forward (Source To Destination)
    LUT = 1,$(FME_MF_DIR)Extended_Building_Quality_Generic_Query_Old_Surveys.sql
    SRC = phase
    VAL_ATTR = _SQL
    -> AttributeFileReader_3
AttributeFileReader_3
    CHAR_ENCODING = utf-8
    DEST_ATTR = _SQL
    FILE_NAME = $(Children_Info_SQL)
    -> StringReplacer_3
StringReplacer_3
    CASE = NO
    FIND_TEXT = {SURVEYID}
    NO_MATCH = _FME_NO_OP_
    REGEXP = NO
    REPLACE_TEXT = @Value(surveyid)
    SRC_ATTRS = _SQL
    -> SQLExecutor_2 [INITIATOR]
    -> StringReplacer_3_Output
