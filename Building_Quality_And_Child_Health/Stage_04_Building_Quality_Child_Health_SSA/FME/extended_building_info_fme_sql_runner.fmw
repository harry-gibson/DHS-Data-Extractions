FME workspace extended_building_info_fme_sql_runner.fmw

Parameters:
- Building_Info_SQL_Phase2-6 = $(FME_MF_DIR_ENCODED)Extended_Building_Quality_Generic_Query_2018.sql   # SQL file for building info in phases 2-6
- Building_Info_SQL_Phase1 = $(FME_MF_DIR)Extended_Building_Quality_Generic_Query_Old_Surveys.sql   # *.sql SQL file for building info in phase 1 surveys
- DestDataset_CSV = C:\Users\zool1301.NDPH\Documents\DHS\Processing_Code\StuntingLucy_201811\out   # Destination CSV (Comma Separated Value) Folder
- SourceDataset_CSV2 = http://api.dhsprogram.com/rest/dhs/surveys?f=csv&surveyStatus=all   # Source CSV (Comma Separated Value) File(s)

Readers:
- XLSXR_1: XLSXR from \\map-fs1.ndph.ox.ac.uk\map_data\DHS_Automation\SupportingInfo\Standard country codes.xlsx
- CSV2_1: CSV2 from $(SourceDataset_CSV2)

Writers:
- CSV_2: CSV to $(DestDataset_CSV)

SQLExecutor_2
    COMBINE_ATTRS = Keep Result Attributes if Conflict
    COMBINE_GEOM = Initiator Geometry Only
    DATASET = DHS Data Readonly
    EXPOSED_ATTRIBUTE_LIST = head_occ_grp,head_occ_grp_desc,hhid,hv000_ccode_phase,hv001_ClusterID,hv002_hhnum,hv005_wt,hv009_nmembers,hv014_nunder5s,hv025_desc_resid_type,hv025_resid_type,hv026_desc_resid_place,hv026_resid_place,hv040_cluster_alt_m,hv106_desc_head_ed_lvl,hv106_head_ed_lvl,hv109_desc_head_ed_attain,hv109_head_ed_attain,hv115_desc_head_marital,hv115_head_marital_status,hv201_desc_watersrc,hv201_watersrc,hv204_mins_to_watersrc,hv205_desc_toilet,hv205_toilet,hv206_has_electric,hv207_has_radio,hv208_has_tv,hv209_has_fridge,hv210_has_bike,hv211_has_mbike,hv212_has_car,hv213_desc_flooring,hv213_flooring,hv214_desc_walling,hv214_walling,hv215_desc_roofing,hv215_roofing,hv216_nbedrooms,hv219_desc_hh_head_sex,hv219_hh_head_sex,hv220_hh_head_age,hv221_hasphone,hv225_sharestoilet,hv226_cooking_fuel,hv226_desc_cooking_fuel,hv238_nhh_sharing_toilet,hv239_cooking_appliance,hv239_desc_cooking_appliance,hv240_desc_ventilation,hv240_ventilation,hv242_has_separate_kitchen,hv243a_hasmobile,hv243b_haswatch,hv243c_hashorsecart,hv243d_hasmotorboat,hv244_has_agri_land,hv245_hect_agri_land_1dec,hv247_has_bankacct,hv252_frequency_of_smoking,hv252_desc_frequency_of_smoking,hv253_irs_in_last_yr,hv270_desc_wealthquint,hv270_wealthquint,hv271_wealthscore,latitude,longitude,n_head_entries,surveyid,who_is_head
    FORMAT = POSTGRES
    POSTGRES_NAMED_CONNECTION = DHS Data Readonly
    POSTGRES_QUERY_FEATURE_TYPES_FOR_MERGE_FILTERS = Yes
    POSTGRES_READ_TIME_WITH_TIMEZONE = Yes
    POSTGRES_SCHEMAS_FOR_TABLE_LISTING = dhs_data_tables
    SQL_STATEMENT = @Value(_SQL)
    RESULT -> AttributeManager_2
    <REJECTED> -> SQLExecutor_2__Rejected_
AttributeManager_2
    ATTR_TABLE:
      REMOVE surveyid
      REMOVE _SQL
      RENAME_SET_VALUE hhid > HHID = Case Identification
      RENAME_SET_VALUE hv000_ccode_phase > HV000 = Country code and phase
      RENAME_SET_VALUE hv001_ClusterID > HV001 = Cluster number
      RENAME_SET_VALUE hv002_hhnum > HV002 = Household number
      RENAME_SET_VALUE hv005_wt > HV005 = Household sample weight (6 decimals)
      RENAME_SET_VALUE hv009_nmembers > HV009 = Number of household members
      RENAME_SET_VALUE hv025_desc_resid_type > HV025 | Type of place of residence
      RENAME_SET_VALUE hv025_resid_type > HV025 = Type of place of residence
      RENAME_SET_VALUE hv201_desc_watersrc > HV201 | Source of drinking water
      RENAME_SET_VALUE hv201_watersrc > HV201 = Source of drinking water
      RENAME_SET_VALUE hv205_desc_toilet > HV205 | Type of toilet facility
      RENAME_SET_VALUE hv205_toilet > HV205 = Type of toilet facility
      RENAME_SET_VALUE hv213_desc_flooring > HV213 | Main floor material
      RENAME_SET_VALUE hv213_flooring > HV213 = Main floor material
      RENAME_SET_VALUE hv214_desc_walling > HV214 | Main wall material
      RENAME_SET_VALUE hv214_walling > HV214 = Main wall material
      RENAME_SET_VALUE hv215_desc_roofing > HV215 | Main roof material
      RENAME_SET_VALUE hv215_roofing > HV215 = Main roof material
      RENAME_SET_VALUE hv216_nbedrooms > HV216 = Number of rooms used for sleeping
      RENAME_SET_VALUE hv221_hasphone > HV221 = Has telephone (land-line)
      RENAME_SET_VALUE hv226_cooking_fuel > HV226 = Type of cooking fuel
      RENAME_SET_VALUE hv226_desc_cooking_fuel > HV226 | Type of cooking fuel
      RENAME_SET_VALUE hv243a_hasmobile > HV243A = Has mobile telephone
      RENAME_SET_VALUE hv243b_haswatch > HV243B = Has watch
      RENAME_SET_VALUE hv243c_hashorsecart > HV243C = Has animal-drawn cart
      RENAME_SET_VALUE hv243d_hasmotorboat > HV243D = NA - Has boat with a motor
      RENAME_SET_VALUE hv244_has_agri_land > HV244 = Owns land usable for agriculture
      RENAME_SET_VALUE hv245_hect_agri_land_1dec > HV245 = Hectares of agricultural land (1 decimal)
      RENAME_SET_VALUE hv247_has_bankacct > HV247 = Has bank account
      RENAME_SET_VALUE hv270_desc_wealthquint > HV270 | Wealth index
      RENAME_SET_VALUE hv270_wealthquint > HV270 = Wealth index
      RENAME_SET_VALUE hv271_wealthscore > HV271 = Wealth index factor score (5 decimals)
      RENAME_SET_VALUE hv014_nunder5s > HV014 = Number Under 5s
      RENAME_SET_VALUE hv026_desc_resid_place > HV026 | Place of Residence
      RENAME_SET_VALUE hv026_resid_place > HV026 = Place of Residence
      RENAME_SET_VALUE hv040_cluster_alt_m > HV040 = Cluster Altitude m
      RENAME_SET_VALUE hv204_mins_to_watersrc > HV204 = Mins to reach water source
      RENAME_SET_VALUE hv206_has_electric > HV206 = Has electricity
      RENAME_SET_VALUE hv207_has_radio > HV207 = Has radio
      RENAME_SET_VALUE hv208_has_tv > HV208 = Has television
      RENAME_SET_VALUE hv209_has_fridge > HV209 = Has refrigerator
      RENAME_SET_VALUE hv210_has_bike > HV210 = Has bicycle
      RENAME_SET_VALUE hv211_has_mbike > HV211 = Has motorcycle/scooter
      RENAME_SET_VALUE hv212_has_car > HV212 = Has car/truck
      RENAME_SET_VALUE hv219_hh_head_sex > HV219 = Sex of household head
      RENAME_SET_VALUE hv219_desc_hh_head_sex > HV219 | Sex of household head
      RENAME_SET_VALUE hv220_hh_head_age > HV220 = Age of household head
      RENAME_SET_VALUE hv225_sharestoilet > HV225 = Shares toilet
      RENAME_SET_VALUE hv238_nhh_sharing_toilet > HV238 = Number of households sharing toilet
      RENAME_SET_VALUE hv239_cooking_appliance > HV239 = Cooking appliance
      RENAME_SET_VALUE hv239_desc_cooking_appliance > HV239 | Cooking appliance
      RENAME_SET_VALUE hv240_desc_ventilation > HV240 | Cooking ventilation
      RENAME_SET_VALUE hv240_ventilation > HV240 = Cooking ventilation
      RENAME_SET_VALUE hv242_has_separate_kitchen > HV242 = Has separate kitchen
      RENAME_SET_VALUE hv252_frequency_of_smoking > HV252 = Frequency of Smoking Indoors
      RENAME_SET_VALUE hv252_desc_frequency_of_smoking > HV252 | Frequency of Smoking Indoors
      RENAME_SET_VALUE hv253_irs_in_last_yr > HV253 = IRS in last 12 months
      RENAME_SET_VALUE hv106_head_ed_lvl > HV106 = Highest Education Lvl HH Head Attained
      RENAME_SET_VALUE hv106_desc_head_ed_lvl > HV106 | Highest Education Lvl HH Head Attained
      RENAME_SET_VALUE hv109_head_ed_attain > HV109 = Education Lvl HH Head
      RENAME_SET_VALUE hv109_desc_head_ed_attain > HV109 | Education Lvl HH Head
      RENAME_SET_VALUE hv115_desc_head_marital > HV115 | Marital Status of HH Head
      RENAME_SET_VALUE hv115_head_marital_status > HV115 = Marital Status of HH Head
      RENAME_SET_VALUE head_occ_grp > V717orV705 = Occupation Group of HH Head
      RENAME_SET_VALUE head_occ_grp_desc > V717orV705 | Occupation Group of HH Head
      RENAME_SET_VALUE n_head_entries > Flag = N entries for HH Head Occ
      RENAME_SET_VALUE who_is_head > Flag2 = HH Head Occ Refers To
      REMOVE hv000
      REMOVE phase
    -> All_P2-6 (writer CSV_2)
All_P2-6 (writer CSV_2)
    attributes: HHID = Case Identification auto, CountryName char(26), DHS_CountryCode char(3), SurveyNum number(4,0), SurveyType char(4), SurveyYear number(5,0), HV000 = Country code and phase auto, HV001 = Cluster number auto, latitude auto, longitude auto, HV002 = Household number auto, HV005 = Household sample weight (6 decimals) auto, HV009 = Number of household members auto, HV025 | Type of place of residence auto, HV025 = Type of place of residence auto, HV201 | Source of drinking water auto, HV201 = Source of drinking water auto, HV205 | Type of toilet facility auto, HV205 = Type of toilet facility auto, HV213 | Main floor material auto, HV213 = Main floor material auto, HV214 | Main wall material auto, HV214 = Main wall material auto, HV215 | Main roof material auto, HV215 = Main roof material auto, HV216 = Number of rooms used for sleeping auto, HV221 = Has telephone (land-line) auto, HV226 = Type of cooking fuel auto, HV226 | Type of cooking fuel auto, HV243A = Has mobile telephone auto,
      HV243B = Has watch auto, HV243C = Has animal-drawn cart auto, HV243D = NA - Has boat with a motor auto, HV244 = Owns land usable for agriculture auto, HV245 = Hectares of agricultural land (1 decimal) auto, HV247 = Has bank account auto, HV270 | Wealth index auto, HV270 = Wealth index auto, HV271 = Wealth index factor score (5 decimals) auto, HV014 = Number Under 5s auto, HV026 | Place of Residence auto, HV026 = Place of Residence auto, HV040 = Cluster Altitude m auto, HV204 = Mins to reach water source auto, HV206 = Has electricity auto, HV207 = Has radio auto, HV208 = Has television auto, HV209 = Has refrigerator auto, HV210 = Has bicycle auto, HV211 = Has motorcycle/scooter auto, HV212 = Has car/truck auto, HV219 = Sex of household head auto, HV219 | Sex of household head auto, HV220 = Age of household head auto, HV225 = Shares toilet auto, HV238 = Number of households sharing toilet auto, HV239 = Cooking appliance auto, HV239 | Cooking appliance auto, HV240 | Cooking ventilation auto, HV240 = Cooking ventilation auto,
      HV242 = Has separate kitchen auto, HV252 = Frequency of Smoking Indoors auto, HV252 | Frequency of Smoking Indoors auto, HV253 = IRS in last 12 months auto, HV106 = Highest Education Lvl HH Head Attained auto, HV106 | Highest Education Lvl HH Head Attained auto, HV109 = Education Lvl HH Head auto, HV109 | Education Lvl HH Head auto, HV115 | Marital Status of HH Head auto, HV115 = Marital Status of HH Head auto, V717orV705 = Occupation Group of HH Head auto, V717orV705 | Occupation Group of HH Head auto, Flag = N entries for HH Head Occ auto, Flag2 = HH Head Occ Refers To auto
SQLExecutor_2__Rejected_: Inspector
StringReplacer_3_Output: Inspector
AttributeFileReader [off]
    CHAR_ENCODING = utf-8
    DEST_ATTR = _SQL
    FILE_NAME = @Value(_SQLFile)
    -> StringReplacer_2
StringReplacer_2 [off]
    CASE = NO
    FIND_TEXT = {SURVEYID}
    NO_MATCH = _FME_NO_OP_
    REGEXP = NO
    REPLACE_TEXT = @Value(Svy_Num)
    SRC_ATTRS = _SQL

Bookmark: Get Phase of all sub-saharan surveys in our DB
Note: HV000 is a combination of country code and phase
SQLCreator
    DATASET = DHS Data Readonly
    EXPOSED_ATTRIBUTE_LIST = hv000,surveyid
    FORMAT = POSTGRES
    POSTGRES_NAMED_CONNECTION = DHS Data Readonly
    POSTGRES_QUERY_FEATURE_TYPES_FOR_MERGE_FILTERS = Yes
    POSTGRES_SCHEMAS_FOR_TABLE_LISTING = dhs_data_locations dhs_data_tables
    SQL_STATEMENT = select distinct surveyid,hv000 from dhs_data_tables."RECH0"
    RESULT -> Tester
    RESULT -> FeatureMerger [REQUESTOR]
Tester
    BOOL_OP = OR
    TEST_CLAUSE = TEST @Value(surveyid) = 289
FeatureMerger
    ATTR_ACCUM_MODE = Merge Supplier
    ATTR_CONFLICT_RES = Use Requestor
    IGNORE_NULLS = No
    JOIN_KEYS = @Value(surveyid) @Value(SurveyNum) AUTO
    MERGE_TYPE = Attributes Only
    PROCESS_DUPS = No
    REJECT_NULL_MISSING_KEYS = No
    SUPPLIERS_FIRST = No
    MERGED -> StringSearcher
StringSearcher
    CASE = no
    MATCHED_RESULT_ATTR = phase
    REGEXP = \d$
    STRING_TO_SEARCH = @Value(hv000)
    MATCHED -> AttributeValueMapper

Bookmark: Get listing of all sub-saharan surveys from the DHS API
CSV (reader CSV2_1)
    attributes: SurveyId string, DHS_CountryCode string, SurveyYear string, SurveyType string, SurveyStatus string, CountryName string, SurveyYearLabel string, SurveyNum string, IndicatorData string, RegionName string, SubregionName string, PublicationDate string, ReleaseDate string, SurveyCharacteristicIds string, Footnotes string, FieldworkStart string, FieldworkEnd string, ImplementingOrg string, NumberOfSamplePoints string, NumberofHouseholds string, UniverseOfWomen string, NumberOfWomen string, MinAgeWomen string, MaxAgeWomen string, UniverseOfMen string, NumberOfMen string, MinAgeMen string, MaxAgeMen string, NumberOfFacilities string
    -> Tester_2
Tester_2
    BOOL_OP = OR
    TEST_CLAUSE = TEST @Value(RegionName) BEGINS_WITH Sub-Saharan
    PASSED -> AttributeKeeper_4
AttributeKeeper_4
    KEEP_ATTRS = CountryName,SurveyType,SurveyYear,DHS_CountryCode,SurveyNum
    -> FeatureMerger [SUPPLIER]

Bookmark: Load the appropriate SQL template for the survey phase
AttributeValueMapper
    DEFAULT_VALUE = $(Building_Info_SQL_Phase2-6)
    DIRECTION = Forward (Source To Destination)
    LUT = 1,$(Building_Info_SQL_Phase1)
    SRC = phase
    VAL_ATTR = _SQL
    -> AttributeFileReader_3
AttributeFileReader_3
    CHAR_ENCODING = fme-binary
    DEST_ATTR = _SQL
    FILE_NAME = $(Building_Info_SQL_Phase2-6)
    -> StringReplacer_3
StringReplacer_3
    CASE = NO
    FIND_TEXT = {SURVEYID}
    NO_MATCH = _FME_NO_OP_
    REGEXP = NO
    REPLACE_TEXT = @Value(surveyid)
    SRC_ATTRS = _SQL
    -> SQLExecutor_2 [INITIATOR]
    -> StringReplacer_3_Output
