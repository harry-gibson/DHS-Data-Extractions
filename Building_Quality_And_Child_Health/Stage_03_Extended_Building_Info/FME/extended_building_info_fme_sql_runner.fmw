FME workspace extended_building_info_fme_sql_runner.fmw

Parameters:
- Building_Info_SQL_Phase2-6 = $(FME_MF_DIR_ENCODED)Extended_Building_Quality_Generic_Query.sql   # SQL file for building info in phases 2-6
- SourceDataset_CSV = \\map-fs1.ndph.ox.ac.uk\map_data\DHS_Automation\DataExtraction\All\SurveyInfo\available_DHS_surveys_20160706.csv   # Source CSV (Comma Separated Value) File(s)
- Building_Info_SQL_Phase1 = $(FME_MF_DIR)Extended_Building_Quality_Generic_Query_Old_Surveys.sql   # *.sql SQL file for building info in phase 1 surveys
- DestDataset_CSV = \\map-fs1.ndph.ox.ac.uk\map_data\DHS_Automation\Processing\Building_Quality_Extended_201608\out   # Destination CSV (Comma Separated Value) Folder

Readers:
- XLSXR_2: XLSXR from \\map-fs1.ndph.ox.ac.uk\map_data\DHS_Automation\SupportingInfo\Standard country codes.xlsx
- CSV_1: CSV from $(SourceDataset_CSV)

Writers:
- CSV_2: CSV to $(DestDataset_CSV)

SQLCreator
    EXPOSED_ATTRIBUTE_LIST = hv000,surveyid
    POSTGRES_NAMED_CONNECTION = DHS Data Readonly
    FORMAT = POSTGRES
    DATASET = DHS Data Readonly
    SQL_STATEMENT = select distinct surveyid,hv000 from dhs_data_tables."RECH0"
    POSTGRES_QUERY_FEATURE_TYPES_FOR_MERGE_FILTERS = Yes
    POSTGRES_SCHEMAS_FOR_TABLE_LISTING = dhs_data_locations dhs_data_tables
    RESULT -> Tester
Tester
    BOOL_OP = OR
    TEST_CLAUSE = TEST @Value(surveyid) = 289
    TEST_MODE = Automatic
    TEST_DESCRIPTION = ""
    PASSED -> FeatureMerger [REQUESTOR]
available_DHS_surveys_20160706 (reader CSV_1)
    attributes: SurveyId char(10), DHS_CountryCode char(3), SurveyYear number(5,0), SurveyType char(4), SurveyStatus char(10), CountryName char(26), SurveyYearLabel char(10), SurveyNum number(4,0), IndicatorData number(2,0), RegionName char(30), SubregionName char(16), PublicationDate char(11), ReleaseDate char(11), SurveyCharacteristicIds char(123), FieldworkStart char(11), FieldworkEnd char(11), ImplementingOrg char(254), NumberOfSamplePoints number(5,0), NumberofHouseholds number(7,0), UniverseOfWomen char(19), NumberOfWomen number(7,0), MinAgeWomen number(3,0), MaxAgeWomen number(3,0), UniverseOfMen char(22), NumberOfMen number(6,0), MinAgeMen number(3,0), MaxAgeMen number(3,0), NumberOfFacilities number(5,0)
    -> Tester_2
Tester_2
    BOOL_OP = OR
    TEST_CLAUSE = TEST @Value(RegionName) BEGINS_WITH Sub-Saharan
    TEST_MODE = Automatic
    TEST_DESCRIPTION = ""
    PASSED -> AttributeKeeper_4
AttributeKeeper_4
    KEEP_ATTRS = CountryName,SurveyType,SurveyYear,DHS_CountryCode,SurveyNum
    -> FeatureMerger [SUPPLIER]
FeatureMerger
    IGNORE_NULLS = No
    ATTR_CONFLICT_RES = Use Requestor
    SUPPLIERS_FIRST = No
    MERGE_TYPE = Attributes Only
    REJECT_NULL_MISSING_KEYS = No
    ATTR_ACCUM_MODE = Merge Supplier
    JOIN_KEYS = @Value(surveyid) @Value(SurveyNum) AUTO
    PROCESS_DUPS = No
    MERGED -> StringSearcher
StringSearcher
    STRING_TO_SEARCH = @Value(hv000)
    MATCHED_RESULT_ATTR = phase
    REGEXP = \d$
    CASE = no
    MATCHED -> AttributeValueMapper
AttributeValueMapper
    LUT = 1,$(Building_Info_SQL_Phase1)
    SRC = phase
    DIRECTION = Forward (Source To Destination)
    VAL_ATTR = _SQL
    DEFAULT_VALUE = $(Building_Info_SQL_Phase2-6)
    -> AttributeFileReader_3
AttributeFileReader_3
    FILE_NAME = $(Building_Info_SQL_Phase2-6)
    DEST_ATTR = _SQL
    CHAR_ENCODING = fme-binary
    -> StringReplacer_3
StringReplacer_3
    NO_MATCH = _FME_NO_OP_
    FIND_TEXT = {SURVEYID}
    REGEXP = NO
    SRC_ATTRS = _SQL
    REPLACE_TEXT = @Value(surveyid)
    CASE = NO
    -> SQLExecutor_2 [INITIATOR]
SQLExecutor_2
    EXPOSED_ATTRIBUTE_LIST = head_occ_grp,head_occ_grp_desc,hhid,hv000_ccode_phase,hv001_ClusterID,hv002_hhnum,hv005_wt,hv009_nmembers,hv014_nunder5s,hv025_desc_resid_type,hv025_resid_type,hv026_desc_resid_place,hv026_resid_place,hv040_cluster_alt_m,hv106_desc_head_ed_lvl,hv106_head_ed_lvl,hv109_desc_head_ed_attain,hv109_head_ed_attain,hv115_desc_head_marital,hv115_head_marital_status,hv201_desc_watersrc,hv201_watersrc,hv204_mins_to_watersrc,hv205_desc_toilet,hv205_toilet,hv206_has_electric,hv207_has_radio,hv208_has_tv,hv209_has_fridge,hv210_has_bike,hv211_has_mbike,hv212_has_car,hv213_desc_flooring,hv213_flooring,hv214_desc_walling,hv214_walling,hv215_desc_roofing,hv215_roofing,hv216_nbedrooms,hv219_desc_hh_head_gender,hv219_hh_head_gender,hv220_hh_head_age,hv221_hasphone,hv225_sharestoilet,hv226_cooking_fuel,hv226_desc_cooking_fuel,hv238_nhh_sharing_toilet,hv239_cooking_appliance,hv239_desc_cooking_appliance,hv240_desc_ventilation,hv240_ventilation,hv242_has_separate_kitchen,hv243a_hasmobile,hv243b_haswatch,hv243c_hashorsecart,hv243d_hasmotorboat,hv244_has_agri_land,hv245_hect_agri_land_1dec,hv247_has_bankacct,hv270_desc_wealthquint,hv270_wealthquint,hv271_wealthscore,latitude,longitude,n_head_entries,surveyid,who_is_head
    POSTGRES_NAMED_CONNECTION = DHS Data Readonly
    FORMAT = POSTGRES
    DATASET = DHS Data Readonly
    SQL_STATEMENT = @Value(_SQL)
    COMBINE_GEOM = Initiator Geometry Only
    POSTGRES_QUERY_FEATURE_TYPES_FOR_MERGE_FILTERS = Yes
    COMBINE_ATTRS = Keep Result Attributes if Conflict
    POSTGRES_SCHEMAS_FOR_TABLE_LISTING = dhs_data_tables
    RESULT -> AttributeManager_2
    <REJECTED> -> SQLExecutor_2__Rejected_
AttributeManager_2
    ATTR_TABLE:
      REMOVE surveyid
      REMOVE _SQL
      RENAME_SET_VALUE hhid > HHID = Case Identification
      RENAME_SET_VALUE hv000_ccode_phase > HV000 = Country code and phase
      RENAME_SET_VALUE hv001_ClusterID > HV001 = Cluster number
      RENAME_SET_VALUE hv002_hhnum > HV002 = Household number
      RENAME_SET_VALUE hv005_wt > HV005 = Household sample weight (6 decimals)
      RENAME_SET_VALUE hv009_nmembers > HV009 = Number of household members
      RENAME_SET_VALUE hv025_desc_resid_type > HV025 | Type of place of residence
      RENAME_SET_VALUE hv025_resid_type > HV025 = Type of place of residence
      RENAME_SET_VALUE hv201_desc_watersrc > HV201 | Source of drinking water
      RENAME_SET_VALUE hv201_watersrc > HV201 = Source of drinking water
      RENAME_SET_VALUE hv205_desc_toilet > HV205 | Type of toilet facility
      RENAME_SET_VALUE hv205_toilet > HV205 = Type of toilet facility
      RENAME_SET_VALUE hv213_desc_flooring > HV213 | Main floor material
      RENAME_SET_VALUE hv213_flooring > HV213 = Main floor material
      RENAME_SET_VALUE hv214_desc_walling > HV214 | Main wall material
      RENAME_SET_VALUE hv214_walling > HV214 = Main wall material
      RENAME_SET_VALUE hv215_desc_roofing > HV215 | Main roof material
      RENAME_SET_VALUE hv215_roofing > HV215 = Main roof material
      RENAME_SET_VALUE hv216_nbedrooms > HV216 = Number of rooms used for sleeping
      RENAME_SET_VALUE hv221_hasphone > HV221 = Has telephone (land-line)
      RENAME_SET_VALUE hv226_cooking_fuel > HV226 = Type of cooking fuel
      RENAME_SET_VALUE hv226_desc_cooking_fuel > HV226 | Type of cooking fuel
      RENAME_SET_VALUE hv243a_hasmobile > HV243A = Has mobile telephone
      RENAME_SET_VALUE hv243b_haswatch > HV243B = Has watch
      RENAME_SET_VALUE hv243c_hashorsecart > HV243C = Has animal-drawn cart
      RENAME_SET_VALUE hv243d_hasmotorboat > HV243D = NA - Has boat with a motor
      RENAME_SET_VALUE hv244_has_agri_land > HV244 = Owns land usable for agriculture
      RENAME_SET_VALUE hv245_hect_agri_land_1dec > HV245 = Hectares of agricultural land (1 decimal)
      RENAME_SET_VALUE hv247_has_bankacct > HV247 = Has bank account
      RENAME_SET_VALUE hv270_desc_wealthquint > HV270 | Wealth index
      RENAME_SET_VALUE hv270_wealthquint > HV270 = Wealth index
      RENAME_SET_VALUE hv271_wealthscore > HV271 = Wealth index factor score (5 decimals)
      RENAME_SET_VALUE hv014_nunder5s > HV014 = Number Under 5s
      RENAME_SET_VALUE hv026_desc_resid_place > HV026 | Place of Residence
      RENAME_SET_VALUE hv026_resid_place > HV026 = Place of Residence
      RENAME_SET_VALUE hv040_cluster_alt_m > HV040 = Cluster Altitude m
      RENAME_SET_VALUE hv204_mins_to_watersrc > HV204 = Mins to reach water source
      RENAME_SET_VALUE hv206_has_electric > HV206 = Has electricity
      RENAME_SET_VALUE hv207_has_radio > HV207 = Has radio
      RENAME_SET_VALUE hv208_has_tv > HV208 = Has television
      RENAME_SET_VALUE hv209_has_fridge > HV209 = Has refrigerator
      RENAME_SET_VALUE hv210_has_bike > HV210 = Has bicycle
      RENAME_SET_VALUE hv211_has_mbike > HV211 = Has motorcycle/scooter
      RENAME_SET_VALUE hv212_has_car > HV212 = Has car/truck
      RENAME_SET_VALUE hv219_desc_hh_head_gender > HV219 | Sex of household head
      RENAME_SET_VALUE hv219_hh_head_gender > HV219 = Sex of household head
      RENAME_SET_VALUE hv220_hh_head_age > HV220 = Age of household head
      RENAME_SET_VALUE hv225_sharestoilet > HV225 = Shares toilet
      RENAME_SET_VALUE hv238_nhh_sharing_toilet > HV238 = Number of households sharing toilet
      RENAME_SET_VALUE hv239_cooking_appliance > HV239 = Cooking appliance
      RENAME_SET_VALUE hv239_desc_cooking_appliance > HV239 | Cooking appliance
      RENAME_SET_VALUE hv240_desc_ventilation > HV240 | Cooking ventilation
      RENAME_SET_VALUE hv240_ventilation > HV240 = Cooking ventilation
      RENAME_SET_VALUE hv242_has_separate_kitchen > HV242 = Has separate kitchen
      RENAME_SET_VALUE hv106_head_ed_lvl > HV106 = Highest Education Lvl HH Head Attained
      RENAME_SET_VALUE hv106_desc_head_ed_lvl > HV106 | Highest Education Lvl HH Head Attained
      RENAME_SET_VALUE hv109_head_ed_attain > HV109 = Education Lvl HH Head
      RENAME_SET_VALUE hv109_desc_head_ed_attain > HV109 | Education Lvl HH Head
      RENAME_SET_VALUE hv115_desc_head_marital > HV115 | Marital Status of HH Head
      RENAME_SET_VALUE hv115_head_marital_status > HV115 = Marital Status of HH Head
      RENAME_SET_VALUE head_occ_grp > V717orV705 = Occupation Group of HH Head
      RENAME_SET_VALUE head_occ_grp_desc > V717orV705 | Occupation Group of HH Head
      RENAME_SET_VALUE n_head_entries > Flag = N entries for HH Head Occ
      RENAME_SET_VALUE who_is_head > Flag2 = HH Head Occ Refers To
      REMOVE hv000
      REMOVE phase
    -> All_P2-6 (writer CSV_2)
All_P2-6 (writer CSV_2)
    attributes: HHID = Case Identification auto, CountryName char(26), DHS_CountryCode char(3), SurveyNum number(4,0), SurveyType char(4), SurveyYear number(5,0), HV000 = Country code and phase auto, HV001 = Cluster number auto, latitude auto, longitude auto, HV002 = Household number auto, HV005 = Household sample weight (6 decimals) auto, HV009 = Number of household members auto, HV025 | Type of place of residence auto, HV025 = Type of place of residence auto, HV201 | Source of drinking water auto, HV201 = Source of drinking water auto, HV205 | Type of toilet facility auto, HV205 = Type of toilet facility auto, HV213 | Main floor material auto, HV213 = Main floor material auto, HV214 | Main wall material auto, HV214 = Main wall material auto, HV215 | Main roof material auto, HV215 = Main roof material auto, HV216 = Number of rooms used for sleeping auto, HV221 = Has telephone (land-line) auto, HV226 = Type of cooking fuel auto, HV226 | Type of cooking fuel auto, HV243A = Has mobile telephone auto,
      HV243B = Has watch auto, HV243C = Has animal-drawn cart auto, HV243D = NA - Has boat with a motor auto, HV244 = Owns land usable for agriculture auto, HV245 = Hectares of agricultural land (1 decimal) auto, HV247 = Has bank account auto, HV270 | Wealth index auto, HV270 = Wealth index auto, HV271 = Wealth index factor score (5 decimals) auto, HV014 = Number Under 5s auto, HV026 | Place of Residence auto, HV026 = Place of Residence auto, HV040 = Cluster Altitude m auto, HV204 = Mins to reach water source auto, HV206 = Has electricity auto, HV207 = Has radio auto, HV208 = Has television auto, HV209 = Has refrigerator auto, HV210 = Has bicycle auto, HV211 = Has motorcycle/scooter auto, HV212 = Has car/truck auto, HV219 | Sex of household head auto, HV219 = Sex of household head auto, HV220 = Age of household head auto, HV225 = Shares toilet auto, HV238 = Number of households sharing toilet auto, HV239 = Cooking appliance auto, HV239 | Cooking appliance auto, HV240 | Cooking ventilation auto, HV240 = Cooking ventilation auto,
      HV242 = Has separate kitchen auto, HV106 = Highest Education Lvl HH Head Attained auto, HV106 | Highest Education Lvl HH Head Attained auto, HV109 = Education Lvl HH Head auto, HV109 | Education Lvl HH Head auto, HV115 | Marital Status of HH Head auto, HV115 = Marital Status of HH Head auto, V717orV705 = Occupation Group of HH Head auto, V717orV705 | Occupation Group of HH Head auto, Flag = N entries for HH Head Occ auto, Flag2 = HH Head Occ Refers To auto
SQLExecutor_2__Rejected_: Inspector
AttributeFileReader
    FILE_NAME = @Value(_SQLFile)
    DEST_ATTR = _SQL
    CHAR_ENCODING = utf-8
    -> StringReplacer_2
StringReplacer_2
    NO_MATCH = _FME_NO_OP_
    FIND_TEXT = {SURVEYID}
    REGEXP = NO
    SRC_ATTRS = _SQL
    REPLACE_TEXT = @Value(Svy_Num)
    CASE = NO
