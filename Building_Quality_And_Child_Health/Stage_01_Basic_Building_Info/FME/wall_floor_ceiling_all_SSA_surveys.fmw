FME workspace wall_floor_ceiling_all_SSA_surveys.fmw

Parameters:
- SourceDataset_CSV = \\map-fs1.ndph.ox.ac.uk\map_data\DHS_Automation\DataExtraction\All\SurveyInfo\available_DHS_surveys_20160706.csv   # Source CSV (Comma Separated Value) File(s)
- SourceDataset_CSV_3 = \\map-fs1.ndph.ox.ac.uk\map_data\DHS_Automation\DataExtraction\All\ParsedSpecs_Concat\SchemaMapperValueSpecs_All_NonRangeValues_Labelled_Wildcarded.csv   # Source CSV (Comma Separated Value) File(s)
- DestDataset_CSV = \\map-fs1.ndph.ox.ac.uk\map_data\DHS_Automation\Processing\Building_Quality_Vs_Infection_PWG_LT_201512\Out\201607_BuildingMaterial_AllSSA   # Destination CSV (Comma Separated Value) Folder

Readers:
- CSV_2: CSV from $(SourceDataset_CSV_3)
- CSV_1: CSV from $(SourceDataset_CSV)

Writers:
- CSV_3: CSV to $(DestDataset_CSV)

SchemaMapperValueSpecs_All_NonRangeValues_Labelled_Wildcarded (reader CSV_2)
    attributes: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
SQLCreator
    POSTGRES_SCHEMAS_FOR_TABLE_LISTING = dhs_data_locations dhs_data_tables
    POSTGRES_NAMED_CONNECTION = DHS Data Readonly
    POSTGRES_QUERY_FEATURE_TYPES_FOR_MERGE_FILTERS = Yes
    SQL_STATEMENT = select distinct(surveyid) from dhs_data_tables."RECH0"
    DATASET = DHS Data Readonly
    FORMAT = POSTGRES
    EXPOSED_ATTRIBUTE_LIST = surveyid
    RESULT -> FeatureMerger [REQUESTOR]
available_DHS_surveys_20160706 (reader CSV_1)
    attributes: SurveyId char(10), DHS_CountryCode char(3), SurveyYear number(5,0), SurveyType char(4), SurveyStatus char(10), CountryName char(26), SurveyYearLabel char(10), SurveyNum number(4,0), IndicatorData number(2,0), RegionName char(30), SubregionName char(16), PublicationDate char(11), ReleaseDate char(11), SurveyCharacteristicIds char(123), FieldworkStart char(11), FieldworkEnd char(11), ImplementingOrg char(254), NumberOfSamplePoints number(5,0), NumberofHouseholds number(7,0), UniverseOfWomen char(19), NumberOfWomen number(7,0), MinAgeWomen number(3,0), MaxAgeWomen number(3,0), UniverseOfMen char(22), NumberOfMen number(6,0), MinAgeMen number(3,0), MaxAgeMen number(3,0), NumberOfFacilities number(5,0)
    -> Tester
Tester
    TEST_DESCRIPTION = ""
    TEST_CLAUSE = TEST @Value(RegionName) BEGINS_WITH Sub-Saharan
    BOOL_OP = OR
    TEST_MODE = Automatic
    PASSED -> AttributeKeeper
AttributeKeeper
    KEEP_ATTRS = CountryName,SurveyType,SurveyYear,DHS_CountryCode,SurveyNum
    -> FeatureMerger [SUPPLIER]
FeatureMerger
    PROCESS_DUPS = No
    ATTR_ACCUM_MODE = Merge Supplier
    ATTR_CONFLICT_RES = Use Requestor
    IGNORE_NULLS = No
    MERGE_TYPE = Attributes Only
    REJECT_NULL_MISSING_KEYS = No
    JOIN_KEYS = @Value(surveyid) @Value(SurveyNum) AUTO
    SUPPLIERS_FIRST = No
    MERGED -> SQLExecutor [INITIATOR]
    MERGED -> AttributeCreator
    UNREFERENCED -> FeatureMerger_Unreferenced
FeatureMerger_Unreferenced: Inspector
AttributeCreator
    ATTR_TABLE = SET_TO _SpecFile = \\map-fs1.ndph.ox.ac.uk\map_data\DHS_Automation\DataExtraction\All\ParsedSpecs\@Value(surveyid).*.FlatValuesSpec.csv
    -> FeatureReader [INITIATOR]
FeatureReader
    CSV__SKIP_FOOTER = 0
    COMBINE_GEOM = Use Result
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__FIELD_NAMES_AFTER_HEADER = no
    CSV__STRIP_QUOTES = yes
    CSV__ALLOW_SPACES_IN_COLUMN_NAMES = yes
    CSV__DUPLICATE_DELIMS = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    FEATURETYPES = CSV
    CSV__IN_SEPARATOR = ,
    ATTRS_TO_EXPOSE = Name Value ValueDesc
    OUTPUT_FEATURES_DISPLAY = Schema and Data Features
    CSV__GROUP_BY_DATASET = no
    CSV_SCAN_MAX_FEATURES = 1000
    CSV__SKIP_LINES = 1
    ATTR_ACCUM_MODE = Merge Initiator and Result
    FORMAT = CSV
    ATTR_CONFLICT_RES = Use Result
    CSV__IN_FIELD_NAMES = YES
    DATASET = @Value(_SpecFile)
    <OTHER> -> AttributeKeeper_2
AttributeKeeper_2
    KEEP_ATTRS = ValueDesc,Name,surveyid,Value
    -> TestFilter
TestFilter
    DEFAULT_VALUE = <UNFILTERED>
    TEST_LIST = BOOL_OP,OR,COMPOSITE_TEST,<Unused>,TEST_CLAUSE,"TEST @Value(Name) = HV213",HV213,BOOL_OP,OR,COMPOSITE_TEST,<Unused>,TEST_CLAUSE,"TEST @Value(Name) = HV214",HV214,BOOL_OP,OR,COMPOSITE_TEST,<Unused>,TEST_CLAUSE,"TEST @Value(Name) = HV215",HV215
    HV213 -> AttributeRenamer
    HV214 -> AttributeRenamer_2
    HV215 -> AttributeRenamer_3
AttributeRenamer
    ATTR_TABLE = RENAME_SET_DEFAULT ValueDesc > HV213_Main_Floor_Material
    -> FeatureMerger_2 [SUPPLIER]
AttributeRenamer_2
    ATTR_TABLE = RENAME_SET_DEFAULT ValueDesc > HV214_Main_Wall_Material
    -> FeatureMerger_3 [SUPPLIER]
AttributeRenamer_3
    ATTR_TABLE = RENAME_SET_DEFAULT ValueDesc > HV215_Main_Roof_Material
    -> FeatureMerger_4 [SUPPLIER]
Sampler
    SAMPLE_MODE = No
    RATE = 1
    SAMPLE_TYPE_LONG = First N Features
    SAMPLED -> SQLExecutor [INITIATOR]
SQLExecutor
    POSTGRES_SCHEMAS_FOR_TABLE_LISTING = dhs_data_locations dhs_data_tables
    POSTGRES_NAMED_CONNECTION = DHS Data Readonly
    POSTGRES_QUERY_FEATURE_TYPES_FOR_MERGE_FILTERS = Yes
    COMBINE_ATTRS = Keep Result Attributes if Conflict
    SQL_STATEMENT:
      SELECT
      r0.surveyid
      , r0.hv001 as clusterid
      , locs.latnum as latitude
      , locs.longnum as longitude
      , r0.hhid
      , r0.hv002 as hh_num
      , r0.hv005 as hh_weight
      , r0.hv012 as hh_dejure_pop
      , r0.hv013 as hh_defacto_pop
      , r2.hv213 --as floor_material
      , r2.hv214 --as wall_material
      , r2.hv215 --as roof_material
      FROM
      dhs_data_tables."RECH0" r0
      INNER JOIN
      dhs_data_tables."RECH2" r2
      ON
      r0.surveyid = r2.surveyid AND r0.hhid = r2.hhid
      LEFT OUTER JOIN
      dhs_data_locations.dhs_cluster_locs locs
      ON r0.surveyid::Integer = locs.surveyid AND r0.hv001::Integer = locs.dhsclust
      WHERE r0.surveyid = '@Value(surveyid)'
      ORDER BY r0.surveyid::Integer, r0.hv001::Integer, hhid
    COMBINE_GEOM = Initiator Geometry Only
    DATASET = DHS Data Readonly
    FORMAT = POSTGRES
    EXPOSED_ATTRIBUTE_LIST = surveyid,clusterid,latitude,longitude,hh_num,hhid,hh_defacto_pop,hh_dejure_pop,hh_weight,hv213,hv214,hv215
    RESULT -> SQLExecutor_Result [off]
    RESULT -> BulkAttributeRenamer [off]
    RESULT -> FeatureMerger_2 [REQUESTOR]
SQLExecutor_Result: Inspector
FeatureMerger_2
    PROCESS_DUPS = No
    ATTR_ACCUM_MODE = Merge Supplier
    ATTR_CONFLICT_RES = Use Requestor
    GROUP_BY = surveyid
    IGNORE_NULLS = No
    MERGE_TYPE = Attributes Only
    REJECT_NULL_MISSING_KEYS = No
    JOIN_KEYS = @Value(hv213) @Value(Value) AUTO @Value(surveyid) @Value(surveyid) AUTO
    SUPPLIERS_FIRST = No
    MERGED -> FeatureMerger_3 [REQUESTOR]
    NOT_MERGED -> FeatureMerger_3 [REQUESTOR]
FeatureMerger_3
    PROCESS_DUPS = No
    ATTR_ACCUM_MODE = Merge Supplier
    ATTR_CONFLICT_RES = Use Requestor
    IGNORE_NULLS = No
    MERGE_TYPE = Attributes Only
    REJECT_NULL_MISSING_KEYS = No
    JOIN_KEYS = @Value(hv214) @Value(Value) AUTO @Value(surveyid) @Value(surveyid) AUTO
    SUPPLIERS_FIRST = No
    MERGED -> FeatureMerger_4 [REQUESTOR]
    NOT_MERGED -> FeatureMerger_4 [REQUESTOR]
FeatureMerger_4
    PROCESS_DUPS = No
    ATTR_ACCUM_MODE = Merge Supplier
    ATTR_CONFLICT_RES = Use Requestor
    IGNORE_NULLS = No
    MERGE_TYPE = Attributes Only
    REJECT_NULL_MISSING_KEYS = No
    JOIN_KEYS = @Value(hv215) @Value(Value) AUTO @Value(surveyid) @Value(surveyid) AUTO
    SUPPLIERS_FIRST = No
    MERGED -> all_building_material_ssa_2 (writer CSV_3)
    NOT_MERGED -> all_building_material_ssa_2 (writer CSV_3)
all_building_material_ssa_2 (writer CSV_3)
    attributes: surveyid auto, DHS_CountryCode auto, SurveyYear auto, CountryName auto, SurveyType auto, clusterid auto, latitude auto, longitude auto, hh_num auto, hhid auto, hh_defacto_pop auto, hh_dejure_pop auto, hh_weight auto, hv213 auto, HV213_Main_Floor_Material auto, hv214 auto, HV214_Main_Wall_Material auto, hv215 auto, HV215_Main_Roof_Material auto
Note: Rename DB attributes to uppercase to match what's recorded in the CSV spec files
BulkAttributeRenamer
    CASE_CHANGE_TYPE = UPPERCASE
    PATTERN_ACTION_DISP = Change Case
    ATTRCHOICE = All Attributes
    -> SchemaMapper
Note: This SchemaMappper is used as a one-stop transformer to make a copy of all coded value attributes, named to include the actual question text and containing the interpreted value descriptions, e.g. cooking fuel = "electricity" rather than "1". / (It could equally do it into the original attributes). / Value mappings are recorded in an external csv table, which was generated from the original DCF dictionary files.
SchemaMapper
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    MAP_ATTRS = """""" ValueDescFieldOut ValueDesc
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    IDXDESTCOL = ""
    IDXSOURCEATTR = fme_feature_type
    IDXSOURCECOL = ""
    CSV__SKIP_FOOTER = 0
    CSV__SCHEMA = char,33,,char,8,,number,4,0,char,10,,char,4,,char,8,,char,7,,number,2,0,char,3,,char,4,,char,3,,number,6,0
    CSV__STRIP_QUOTES = yes
    IDXDESTATTR = fme_feature_type
    CSV__ALLOW_SPACES_IN_COLUMN_NAMES = yes
    ROW_ID_ATTR = _schemamapper_row_ids
    CSV__IN_FIELD_NAMES = YES
    CSV_SCAN_MAX_FEATURES = 1000
    MATCH_ATTRS = SurveyIdColumnNameInData SurveyID ValueFieldIn Value
    DATASET = \\map-fs1.ndph.ox.ac.uk\map_data\DHS_Automation\DataExtraction\All\ParsedSpecs_Concat\SchemaMapperValueSpecs_All_NonRangeValues_Labelled_Wildcarded.csv
    FORMAT = CSV
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    TABLE = SchemaMapperValueSpecs_All_NonRangeValues_Labelled_Wildcarded
    CSV__IN_SEPARATOR = ,
    CSV__FIELD_NAMES_AFTER_HEADER = no
    CSV__DUPLICATE_DELIMS = no
    CSV__GROUP_BY_DATASET = yes
    CSV__SKIP_LINES = 1
    MAPPED -> SchemaMapper_Mapped
SchemaMapper_Mapped: Inspector
