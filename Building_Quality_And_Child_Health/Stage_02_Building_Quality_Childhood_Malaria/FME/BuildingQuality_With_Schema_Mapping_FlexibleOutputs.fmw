FME workspace BuildingQuality_With_Schema_Mapping_FlexibleOutputs.fmw

Parameters:
- SourceDataset_CSV = C:\Users\zool1301\Documents\DHS\DHS_Info\SurveyIDs_With_Country_Details.csv   # Source CSV (CommaSeparatedValue) File(s)
- SourceDataset_CSV_3 = \\129.67.26.176\map_data\DHS_Automation\SupportingInfo\Standard country codes Sub Saharan Africa.csv   # Source CSV (CommaSeparatedValue) File(s)
- DestDataset_CSV_2 = \\129.67.26.176\map_data\DHS_Automation\Processing\Building_Quality_Vs_Infection_PWG_LT_201512\Out\Rerun_SingleOutput   # Destination CSV (CommaSeparatedValue) Folder
- DestDataset_CSV = \\129.67.26.176\map_data\DHS_Automation\Processing\Building_Quality_Vs_Infection_PWG_LT_201512\Out\Rerun_SingleOutput   # Destination CSV (CommaSeparatedValue) Folder
- SingleSurveyNumber = 337   # Run for a single survey id?
- RunAllSurveys = True   # Run for all surveys
- SingleOutputFile = Single   # Output to single file or one file per survey?

Readers:
- CSV_1: CSV from $(SourceDataset_CSV)
- CSV_2: CSV from $(SourceDataset_CSV_3)

Writers:
- CSV_3: CSV to $(DestDataset_CSV_2)
- CSV_4: CSV to $(DestDataset_CSV)

Note: Write the data in the native form i.e. with coded attribute names and values
File1 (writer CSV_4)
    attributes: YEAR auto, SURVEY_ID_NUM auto, TYPE auto, ISO3 char(4), SURVEYID auto, HHID auto, HV000 auto, HV001 auto, HV002 auto, HV005 auto, HV009 auto, HV025 auto, HV201 auto, HV205 auto, HV206 auto, HV207 auto, HV208 auto, HV209 auto, HV210 auto, HV211 auto, HV212 auto, HV213 auto, HV214 auto, HV215 auto, HV216 auto, HV221 auto, HV226 auto, HV238 auto, HV243A auto, HV243B auto,
      HV243C auto, HV243D auto, HV244 auto, HV245 auto, HV246 auto, HV247 auto, HV253 auto, HV270 auto, HV271 auto
Sampler_3
    GROUP_BY = !_OUTNAME_LABELLED
    RATE = 1
    SAMPLE_TYPE_LONG = First N Features
    SAMPLED -> AttributeRemover
Note: The first section of this workspace(not the schema mapped part) is equivalent to the following query / SELECT / r0.surveyid, / r0.hhid, / r0.hv001, / r0.hv002, / r0.hv005, / r0.hv009, / r0.hv025, / r2.hv213, / r2.hv215, / r2.hv214, / r2.hv216, / r2.hv253, / r2.hv270, / r2.hv271, / r2.hv201, / r2.hv205, / r2.hv238, / r2.hv226, / r2.hv244, / r2.hv245, / r2.hv246 / FROM / dhs_data_tables."RECH0" r0 / INNER JOIN / dhs_data_tables."RECH2" r2 / ON / r0.surveyid = r2.surveyid / AND / r0.hhid = r2.hhid
AttributeRemover
    REMOVE_ATTRS = ISO3,SURVEY_ID_NUM,SURVEYID,TYPE,YEAR
    -> AttributeExploder_2
AttributeExploder_2
    ATTR_NAME_LABEL = _attr_name
    ATTR_VALUE_LABEL = _attr_value
    KEEP_ATTRIBUTES = Yes
    EXPLODING_TYPE = Features
    KEEP_GEOMETRY = No
    -> AttributeKeeper_6
AttributeKeeper_6
    KEEP_ATTRS = !_OUTNAME_LABELLED,_attr_name,_attr_value
    -> FeatureMerger_3 [SUPPLIER]
Note: Attach the schema info to the remapped features
FeatureMerger_2
    PROCESS_DUPS = No
    MERGE_TYPE = Attributes Only
    SUPPLIERS_FIRST = No
    JOIN_KEYS = @Value(!_OUTNAME_LABELLED) @Value(!_OUTNAME_LABELLED) AUTO
    ATTR_CONFLICT_RES = Use Requestor
    ATTR_ACCUM_MODE = Merge Supplier
    IGNORE_NULLS = No
    MERGED -> File1 (writer CSV_3)
Note: Write the data including the interpreted columns as well as the renamed coded ones
File1 (writer CSV_3)

Bookmark: Get the IDs and related info (country code) of the SSA surveys
SurveyIDs_With_Country_Details (reader CSV_1)
    attributes: Country char(33), Year char(8), Survey_ID_num number(4,0), SurveyAPI_ID char(10), Type char(4), Dataset range min char(8), Dataset range max char(7), IgnoreDupe number(2,0), DHS char(3), ISO3 char(4), ISO2 char(3), GAUL number(6,0)
    -> FeatureMerger [REQUESTOR]
Standard country codes Sub Saharan Africa (reader CSV_2)
    attributes: Shortname char(33), Official Name char(49), ISO3 char(4), ISO2 char(3), UNI number(4,0), UNDP char(4), FAOSTAT number(4,0), GAUL number(4,0), DHS char(3), SSA number(2,0)
    -> AttributeKeeper
AttributeKeeper
    KEEP_ATTRS = ISO3
    -> FeatureMerger [SUPPLIER]
FeatureMerger
    PROCESS_DUPS = No
    MERGE_TYPE = Attributes Only
    SUPPLIERS_FIRST = No
    JOIN_KEYS = @Value(ISO3) @Value(ISO3) AUTO
    ATTR_CONFLICT_RES = Use Requestor
    ATTR_ACCUM_MODE = Merge Supplier
    IGNORE_NULLS = No
    MERGED -> Sampler_2
Note: testing: if required set this appropriately to just run on a few surveys
Sampler_2
    RATE = 1
    SAMPLE_TYPE_LONG = Every Nth Feature
    SAMPLED -> Tester_2
Tester_2
    BOOL_OP = OR
    TEST_MODE = Automatic
    TEST_CLAUSE:
      TEST @Value(Survey_ID_num) = $(SingleSurveyNumber)
      TEST $(RunAllSurveys) = True
    TEST_DESCRIPTION = ""
    PASSED -> ParameterFetcher
ParameterFetcher
    ATTR_LIST = _SingleOutputFile {$(SingleOutputFile)}
    -> AttributeValueMapper
AttributeValueMapper
    SRC = _SingleOutputFile
    DIRECTION = Forward (Source To Destination)
    LUT = Multiple,@Value(Survey_ID_num)_@Value(ISO3)_@Value(Type)_@Value(Year)_ChildMalaria,Single,All_ChildMalaria
    VAL_ATTR = _OutFileTag
    -> AttributeKeeper_2
AttributeKeeper_2
    KEEP_ATTRS = ISO3,Survey_ID_num,Type,Year,_OutFileTag
    -> FeatureReader [INITIATOR]

Bookmark: Read the RECH0 household data
FeatureReader
    POSTGRES_QUERY_FEATURE_TYPES_FOR_MERGE_FILTERS = Yes
    ATTR_ACCUM_MODE = Merge Initiator and Result
    COMBINE_GEOM = Use Result
    POSTGRES_NAMED_CONNECTION = staging@map.zoo.ox.ac.uk:5434/dhs_data_pit
    WHERE = surveyid = @Value(Survey_ID_num)
    POSTGRES_SCHEMALIST = dhs_data_tables
    ATTRIBUTES = dhs_data_tables.RECH0,"surveyid,hhid,hv000,hv001,hv002,hv002a,hv003,hv004,hv005,hv006,hv007,hv008,hv009,hv010,hv011,hv012,hv013,hv014,hv015,hv016,hv017,hv018,hv019,hv020,hv021,hv022,hv023,hv024,hv025,hv026,hv027,hv028,hv030,hv031,hv032,hv033,hv035,hv040,hv041,hv042,hv043,hv044"
    FEATURETYPES = dhs_data_tables.RECH0
    FORMAT = POSTGRES
    ATTR_CONFLICT_RES = Use Result
    DATASET = staging@map.zoo.ox.ac.uk:5434/dhs_data_pit
    OUTPUT_FEATURES_DISPLAY = Based on Connections
    FEATURETYPES_RADIO = FEATURETYPES
    dhs_data_tables.RECH0 -> AttributeKeeper_3
    <REJECTED> -> FeatureReader__Rejected_
FeatureReader__Rejected_: Inspector
AttributeKeeper_3
    KEEP_ATTRS = hhid,hv000,hv001,hv002,hv005,hv009,hv025,ISO3,Survey_ID_num,surveyid,Type,Year,_OutFileTag
    -> Joiner

Bookmark: Attach the RECH2 data to them
Joiner
    MATCH_RULE_DISPLAY = Must Match Zero or One (1:0..1)
    PREFETCH_EXHAUSTIVE = Yes
    TABLE = dhs_data_tables.RECH2
    POSTGRES_SCHEMAS_FOR_TABLE_LISTING = dhs_data_tables
    ADDED_FIELDS = hv201 hv205 hv206 hv207 hv208 hv209 hv210 hv211 hv212 hv213 hv214 hv215 hv216 hv221 hv226 hv238 hv243a hv243b hv243c hv243d hv244 hv245 hv246 hv247 hv253 hv270 hv271
    DATASET = mapprod1-dev-dhsdata
    JOIN_KEYS = hhid hhid surveyid surveyid
    POSTGRES_NAMED_CONNECTION = mapprod1-dev-dhsdata
    FORMAT = POSTGRES
    POSTGRES_QUERY_FEATURE_TYPES_FOR_MERGE_FILTERS = Yes
    CACHE_SIZE = 1000000
    JOINED -> AttributeCreator
Note: Generate the output filenames
AttributeCreator
    ATTR_LIST = !_outname,@Value(_OutFileTag),!_outname_labelled,@Value(_OutFileTag)_Labelled
    -> BulkAttributeRenamer
Note: Rename DB attributes to uppercase to match what's recorded in the CSV spec files
BulkAttributeRenamer
    ATTRCHOICE = All Attributes
    PATTERN_ACTION_DISP = Change Case
    CASE_CHANGE_TYPE = UPPERCASE
    -> File1 (writer CSV_4)
    -> SchemaMapper
    -> Sampler_3

Bookmark: Interpret attr names / values
Note: This SchemaMappper is used as a one-stop transformer to make a copy of all coded value attributes, named to include the actual question text and containing the interpreted value descriptions, e.g. cooking fuel = "electricity" rather than "1". / (It could equally do it into the original attributes). / Value mappings are recorded in an external csv table, which was generated from the original DCF dictionary files.
SchemaMapper
    IDXDESTCOL = ""
    IDXSOURCEATTR = fme_feature_type
    IDXDESTATTR = fme_feature_type
    CSV__DUPLICATE_DELIMS = no
    TABLE = SchemaMapperValueSpecs_All_NonRangeValues_Labelled_Wildcarded
    CSV__SKIP_FOOTER = 0
    CSV__IN_FIELD_NAMES = YES
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    IDXSOURCECOL = ""
    CSV__SCHEMA = char,33,,char,8,,number,4,0,char,10,,char,4,,char,8,,char,7,,number,2,0,char,3,,char,4,,char,3,,number,6,0
    CSV__GROUP_BY_DATASET = yes
    CSV__ALLOW_SPACES_IN_COLUMN_NAMES = yes
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    DATASET = \\map-fs1.ndph.ox.ac.uk\map_data\DHS_Automation\DataExtraction\All\ParsedSpecs_Concat\SchemaMapperValueSpecs_All_NonRangeValues_Labelled_Wildcarded.csv
    CSV__FIELD_NAMES_AFTER_HEADER = no
    CSV_SCAN_MAX_FEATURES = 1000
    MAP_ATTRS = """""" ValueDescFieldOut ValueDesc
    ROW_ID_ATTR = _schemamapper_row_ids
    FORMAT = CSV
    MATCH_ATTRS = SurveyIdColumnNameInData SurveyID ValueFieldIn Value
    CSV__SKIP_LINES = 1
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__STRIP_QUOTES = yes
    CSV__IN_SEPARATOR = ,
    MAPPED -> SchemaMapper_2
    UNMAPPED -> SchemaMapper_MappingNotFound
Note: This SchemaMapper is used to rename the original (numeric) valued attributes, to suffix the actual question text separated from the var name by " = "
SchemaMapper_2
    IDXDESTCOL = ""
    IDXSOURCEATTR = fme_feature_type
    IDXDESTATTR = fme_feature_type
    CSV__DUPLICATE_DELIMS = no
    TABLE = SchemaMapperValueSpecs_All_NonRangeValues_Labelled_Wildcarded
    CSV__SKIP_FOOTER = 0
    CSV__IN_FIELD_NAMES = YES
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    IDXSOURCECOL = ""
    CSV__SCHEMA = char,33,,char,8,,number,4,0,char,10,,char,4,,char,8,,char,7,,number,2,0,char,3,,char,4,,char,3,,number,6,0
    CSV__GROUP_BY_DATASET = yes
    CSV__ALLOW_SPACES_IN_COLUMN_NAMES = yes
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    DATASET = \\map-fs1.ndph.ox.ac.uk\map_data\DHS_Automation\DataExtraction\All\ParsedSpecs_Concat\SchemaMapperValueSpecs_All_NonRangeValues_Labelled_Wildcarded.csv
    CSV__FIELD_NAMES_AFTER_HEADER = no
    CSV_SCAN_MAX_FEATURES = 1000
    MAP_ATTRS = ValueFieldIn ValueFieldOut """"""
    ROW_ID_ATTR = _schemamapper_row_ids
    FORMAT = CSV
    MATCH_ATTRS = SurveyIdColumnNameInData SurveyID
    CSV__SKIP_LINES = 1
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__STRIP_QUOTES = yes
    CSV__IN_SEPARATOR = ,
    MAPPED -> FeatureMerger_2 [REQUESTOR]
    MAPPED -> Sampler
    UNMAPPED -> SchemaMapper_2_Unmapped
SchemaMapper_2_Unmapped: Inspector
SchemaMapper_MappingNotFound: Inspector

Bookmark: Generate output schema info for writer
Note: Because the schema mapper generates new attributes on the fly the workbench doesn't know their names so the writer for these needs to be dynamic. This requires instructions on what the output attribute names should be: generate one copy of this for each output file
Note: Get one per survey (not all surveys have all variables, so even though we're running all to a single file we need to sample one per survey then remove duplicates). Not one per outname as with single-file this wouldn't work.
Sampler
    GROUP_BY = SURVEY_ID_NUM
    RATE = 1
    SAMPLE_TYPE_LONG = First N Features
    SAMPLED -> BulkAttributeRenamer_2
Note: Add a prefix to survey id attribs
BulkAttributeRenamer_2
    REPLACE_STR = !_
    ATTRCHOICE = Selected Attributes
    ATTRLIST = ISO3 SURVEY_ID_NUM SURVEYID TYPE YEAR
    PATTERN_ACTION_DISP = Add String Prefix
    -> AttributeExploder
Note: Convert to one feature per attribute
AttributeExploder
    ATTR_NAME_LABEL = name
    ATTR_VALUE_LABEL = _attr_value
    KEEP_ATTRIBUTES = Yes
    EXPLODING_TYPE = Features
    KEEP_GEOMETRY = No
    -> Tester_3
Note: Separate out survey id attribs from real data
Tester_3
    BOOL_OP = OR
    TEST_MODE = Automatic
    TEST_CLAUSE = TEST @Value(name) BEGINS_WITH !_
    TEST_DESCRIPTION = ""
    PASSED -> DuplicateRemover_2
    FAILED -> AttributeKeeper_5
DuplicateRemover_2
    KEYATTR = name !_OUTNAME_LABELLED
    UNIQUE -> AttributeKeeper_4
Note: Keep only the attribute exploder output, not the original attributes
AttributeKeeper_5
    KEEP_ATTRS = _attr_value,name,!_OUTNAME_LABELLED
    -> StringSearcher
Note: Fiind the original variable name, without the question text added by the schemamappers
StringSearcher
    MATCHED_RESULT_ATTR = _origName
    CASE = no
    REGEXP = ^\w+
    STRING_TO_SEARCH = @Value(name)
    MATCHED_PARTS_ATTR = _blah
    MATCHED -> Tester_5
Note: Drop the original (unrenamed) copies
Tester_5
    BOOL_OP = OR
    TEST_MODE = Automatic
    TEST_CLAUSE = TEST @Value(_origName) = @Value(name)
    TEST_DESCRIPTION = ""
    FAILED -> DuplicateRemover
Note: Keep only one copy of each attribute per output file (only one file in this version!)
DuplicateRemover
    KEYATTR = name !_OUTNAME_LABELLED
    UNIQUE -> FeatureMerger_3 [REQUESTOR]
    UNIQUE -> DuplicateRemover_Unique
Note: The second schemamapper creates an attribute for everything in the mapping, not just what's required / in the data. Use the attributes from before the schemamapper to select only the renamed attributes that should be kept (written to the output)
FeatureMerger_3
    PROCESS_DUPS = No
    MERGE_TYPE = Attributes Only
    SUPPLIERS_FIRST = No
    JOIN_KEYS = @Value(_origName) @Value(_attr_name) AUTO @Value(!_OUTNAME_LABELLED) @Value(!_OUTNAME_LABELLED) AUTO
    ATTR_CONFLICT_RES = Use Requestor
    ATTR_ACCUM_MODE = Merge Supplier
    IGNORE_NULLS = No
    MERGED -> AttributeKeeper_4
Note: Tidy up
AttributeKeeper_4
    KEEP_ATTRS = name,!_OUTNAME_LABELLED
    -> Sorter
Note: Sort, using the !_ prefix to ensure that the survey id attributes go before the data attributes.
Sorter
    SORT_PARM = !_OUTNAME_LABELLED ALPHA ASCENDING name ALPHA ASCENDING
    SORTED -> StringReplacer
Note: Get rid of the !_ prefix
StringReplacer
    CASE = no
    FIND_TEXT = ^!_
    REGEXP = yes
    NO_MATCH = _FME_NO_OP_
    SRC_ATTRS = name
    -> AttributeCreator_2
Note: set the data type for all attributes to be fme_buffer (equiv to text)
AttributeCreator_2
    ATTR_LIST = fme_data_type,fme_buffer
    -> Tester
Note: Don't keep the outname attribute as one to be written in itself
Tester
    BOOL_OP = OR
    TEST_MODE = Automatic
    TEST_CLAUSE:
      TEST @Value(name) BEGINS_WITH fme
      TEST @Value(name) BEGINS_WITH !_
      TEST @Value(name) CONTAINS OUTNAME
    TEST_DESCRIPTION = ""
    FAILED -> ListBuilder
Note: create the attribute{} list for the dynamic writer
ListBuilder
    LIST_NAME = attribute
    GRP_BY = !_OUTNAME_LABELLED
    -> FeatureMerger_2 [SUPPLIER]
    -> ListBuilder_Output
ListBuilder_Output: Inspector
DuplicateRemover_Unique: Inspector
