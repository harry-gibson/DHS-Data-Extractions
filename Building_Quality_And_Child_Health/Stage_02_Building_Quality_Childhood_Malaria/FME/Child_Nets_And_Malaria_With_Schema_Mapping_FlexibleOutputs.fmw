FME workspace Child_Nets_And_Malaria_With_Schema_Mapping_FlexibleOutputs.fmw

Parameters:
- SourceDataset_CSV = C:\Users\zool1301.NDPH\Documents\DHS\DHS_Info\SurveyIDs_With_Country_Details.csv   # Source CSV (CommaSeparatedValue) File(s)
- SourceDataset_CSV_3 = \\map-fs1.ndph.ox.ac.uk\map_data\DHS_Automation\SupportingInfo\Standard country codes Sub Saharan Africa.csv   # Source CSV (CommaSeparatedValue) File(s)
- DestDataset_CSV_2 = \\129.67.26.176\map_data\DHS_Automation\Processing\Building_Quality_Vs_Infection_PWG_LT_201512\Out\Rerun_SingleWriterTest   # Destination CSV (CommaSeparatedValue) Folder
- DestDataset_CSV = \\129.67.26.176\map_data\DHS_Automation\Processing\Building_Quality_Vs_Infection_PWG_LT_201512\Out\Rerun_SingleWriterTest   # Destination CSV (CommaSeparatedValue) Folder
- SingleOutputFile = Multiple   # Output to single file or one file per survey?
- SingleSurver = 282   # ID of a single survey from the file to run for?

Readers:
- CSV_1: CSV from $(SourceDataset_CSV)
- CSV_2: CSV from $(SourceDataset_CSV_3)

Writers:
- CSV_3: CSV to $(DestDataset_CSV_2)
- CSV_4: CSV to $(DestDataset_CSV)

Note: The first section of this workspace(not the schema mapped part) is equivalent to the following query / SELECT / r1.surveyid, / r1.hhid, / r1.hvidx, / r1.hv104, / r1.hv105, / r0.hv001, / r0.hv002, / rm.hml19, / rm.hml20, / rm.hml32, / rm.hml33, / rm.hml35, / rc.hc53, / rc.hc56, / rc.hc57 / FROM / dhs_data_tables."RECH1" r1 / LEFT JOIN / dhs_data_table."RECH0" r0 / ON r1.surveyid = r0.surveyid AND r1.hhid = / r0.hhid / LEFT JOIN / dhs_data_tables."RECHMH" rm / ON r1.surveyid = rm.surveyid AND r1.hhid = rm.hhid AND r1.hvidx = text(rm.hmhidx) / LEFT JOIN / dhs_data_tables."RECH6" rc / ON r1.surveyid = rc.surveyid AND r1.hhid = rc.hhid AND r1.hvidx = rc.idxh6 / WHERE / -- r1.surveyid=211 AND / r1.hv105 < 18
SurveyIDs_With_Country_Details (reader CSV_1)
    attributes: Country char(33), Year char(8), Survey_ID_num number(4,0), SurveyAPI_ID char(10), Type char(4), Dataset range min char(8), Dataset range max char(7), IgnoreDupe number(2,0), DHS char(3), ISO3 char(4), ISO2 char(3), GAUL number(6,0)
    -> Tester_2
Tester_2
    TEST_CLAUSE:
      TEST $(SingleSurver) NOT_CONTAINS_REGEX \d+
      TEST @Value(Survey_ID_num) = $(SingleSurver)
    TEST_MODE = Automatic
    TEST_DESCRIPTION = ""
    BOOL_OP = OR
    PASSED -> FeatureMerger [REQUESTOR]
Note: Write the data in the native form i.e. with coded attribute names and values
File1 (writer CSV_4)
    attributes: YEAR auto, SURVEY_ID_NUM auto, TYPE auto, ISO3 char(4), SURVEYID auto, HHID auto, HVIDX auto, CHILDID auto, HV104 auto, HV105 auto, HML19 auto, HML20 auto, HML32 auto, HML33 auto, HML35 auto, HC53 auto, HC56 auto, HC57 auto
Sampler_3
    GROUP_BY = !_OUTNAME_LABELLED
    RATE = 1
    SAMPLE_TYPE_LONG = First N Features
    SAMPLED -> AttributeRemover
AttributeRemover
    REMOVE_ATTRS = ISO3,SURVEY_ID_NUM,SURVEYID,TYPE,YEAR
    -> AttributeExploder_2
AttributeExploder_2
    ATTR_VALUE_LABEL = _attr_value
    EXPLODING_TYPE = Features
    KEEP_ATTRIBUTES = Yes
    ATTR_NAME_LABEL = _attr_name
    KEEP_GEOMETRY = No
    -> AttributeKeeper_6
AttributeKeeper_6
    KEEP_ATTRS = !_OUTNAME_LABELLED,_attr_name,_attr_value
    -> FeatureMerger_3 [SUPPLIER]
Note: Attach the schema info to the remapped features
FeatureMerger_2
    JOIN_KEYS = @Value(!_OUTNAME_LABELLED) @Value(!_OUTNAME_LABELLED) AUTO
    MERGE_TYPE = Attributes Only
    ATTR_ACCUM_MODE = Merge Supplier
    ATTR_CONFLICT_RES = Use Requestor
    PROCESS_DUPS = No
    SUPPLIERS_FIRST = No
    IGNORE_NULLS = No
    MERGED -> File1 (writer CSV_3)
Note: Write the data including the interpreted columns as well as the native ones
File1 (writer CSV_3)

Bookmark: Get the IDs and related info (country code) of the SSA surveys
Standard country codes Sub Saharan Africa (reader CSV_2)
    attributes: Shortname char(33), Official Name char(49), ISO3 char(4), ISO2 char(3), UNI number(4,0), UNDP char(4), FAOSTAT number(4,0), GAUL number(4,0), DHS char(3), SSA number(2,0)
    -> AttributeKeeper
AttributeKeeper
    KEEP_ATTRS = ISO3
    -> FeatureMerger [SUPPLIER]
FeatureMerger
    JOIN_KEYS = @Value(ISO3) @Value(ISO3) AUTO
    MERGE_TYPE = Attributes Only
    ATTR_ACCUM_MODE = Merge Supplier
    ATTR_CONFLICT_RES = Use Requestor
    PROCESS_DUPS = No
    SUPPLIERS_FIRST = No
    IGNORE_NULLS = No
    MERGED -> Sampler_2
Note: testing: just run on a few surveys
Sampler_2
    RATE = 1
    SAMPLE_TYPE_LONG = Every Nth Feature
    SAMPLED -> ParameterFetcher
ParameterFetcher
    ATTR_LIST = _SingleOutputFile {$(SingleOutputFile)}
    -> AttributeValueMapper
AttributeValueMapper
    LUT = Multiple,@Value(Survey_ID_num)_@Value(ISO3)_@Value(Type)_@Value(Year)_ChildMalaria,Single,All_ChildMalaria
    SRC = _SingleOutputFile
    DIRECTION = Forward (Source To Destination)
    VAL_ATTR = _OutFileTag
    -> AttributeKeeper_2
AttributeKeeper_2
    KEEP_ATTRS = ISO3,Survey_ID_num,Type,Year,_OutFileTag
    -> FeatureReader [INITIATOR]

Bookmark: Read the RECH1 household schedule
FeatureReader
    FORMAT = POSTGRES
    POSTGRES_NAMED_CONNECTION = DHS Data Readonly
    ATTR_CONFLICT_RES = Use Result
    WHERE = surveyid = '@Value(Survey_ID_num)' and hv105::Integer < 18
    ATTR_ACCUM_MODE = Merge Initiator and Result
    COMBINE_GEOM = Use Result
    ATTRIBUTES = dhs_data_tables.RECH1,"surveyid,hhid,hvidx,hv101,hv102,hv103,hv104,hv105,hv106,hv107,hv108,hv109,hv110,hv117,hv111,hv120,hv112,hv113,hv114,hv115,hv116,hv118,hv121,hv122,hv123,hv124,hv125,hv126,hv127,hv128,hv129,hv140,hv130,hv131,hv132,hv133,hv134,hv135,hv136,hv137,hv138,hv139"
    FEATURETYPES = dhs_data_tables.RECH1
    POSTGRES_QUERY_FEATURE_TYPES_FOR_MERGE_FILTERS = Yes
    OUTPUT_FEATURES_DISPLAY = Based on Connections
    FEATURETYPES_RADIO = FEATURETYPES
    DATASET = DHS Data Readonly
    dhs_data_tables.RECH1 -> AttributeKeeper_3
AttributeKeeper_3
    KEEP_ATTRS = hhid,hv104,hv105,hvidx,ISO3,Survey_ID_num,surveyid,Type,Year,_OutFileTag
    -> Joiner_3

Bookmark: Attach the RECH0 / RECH6 / RECHMH data to them
Joiner_3
    JOIN_KEYS = hhid hhid surveyid surveyid
    POSTGRES_NAMED_CONNECTION = DHS Data Readonly
    MATCH_RULE_DISPLAY = Must Match Exactly One (1:1)
    CACHE_SIZE = 5000000
    ADDED_FIELDS = hv001 hv002
    DATASET = DHS Data Readonly
    PREFETCH_EXHAUSTIVE = Yes
    FORMAT = POSTGRES
    POSTGRES_QUERY_FEATURE_TYPES_FOR_MERGE_FILTERS = Yes
    TABLE = dhs_data_tables.RECH0
    JOINED -> Joiner_4
Joiner_4
    JOIN_KEYS = hhid hhid surveyid surveyid hvidx hmhidx
    POSTGRES_NAMED_CONNECTION = DHS Data Readonly
    MATCH_RULE_DISPLAY = Must Match Zero or One (1:0..1)
    CACHE_SIZE = 5000000
    ADDED_FIELDS = hml19 hml20 hml32 hml33 hml35
    DATASET = DHS Data Readonly
    PREFETCH_EXHAUSTIVE = Yes
    FORMAT = POSTGRES
    POSTGRES_QUERY_FEATURE_TYPES_FOR_MERGE_FILTERS = Yes
    TABLE = dhs_data_tables.RECHML
    JOINED -> Joiner
Joiner
    JOIN_KEYS = hhid hhid surveyid surveyid hvidx hmldx
    POSTGRES_NAMED_CONNECTION = DHS Data Readonly
    MATCH_RULE_DISPLAY = Must Match Zero or One (1:0..1)
    CACHE_SIZE = 5000000
    ADDED_FIELDS = hml19 hml20 hml32 hml33 hml35
    DATASET = DHS Data Readonly
    PREFETCH_EXHAUSTIVE = Yes
    FORMAT = POSTGRES
    POSTGRES_QUERY_FEATURE_TYPES_FOR_MERGE_FILTERS = Yes
    TABLE = dhs_data_tables.RECHM2
    JOINED -> Joiner_2
Joiner_2
    JOIN_KEYS = hhid hhid surveyid surveyid hvidx idxh6
    POSTGRES_NAMED_CONNECTION = DHS Data Readonly
    MATCH_RULE_DISPLAY = Must Match Zero or One (1:0..1)
    CACHE_SIZE = 5000000
    ADDED_FIELDS = hc53 hc56 hc57
    DATASET = DHS Data Readonly
    PREFETCH_EXHAUSTIVE = Yes
    FORMAT = POSTGRES
    POSTGRES_QUERY_FEATURE_TYPES_FOR_MERGE_FILTERS = Yes
    TABLE = dhs_data_tables.RECH6
    JOINED -> BulkAttributeRenamer
Note: Rename DB attributes to uppercase to match what's recorded in the CSV spec files
BulkAttributeRenamer
    PATTERN_ACTION_DISP = Change Case
    CASE_CHANGE_TYPE = UPPERCASE
    ATTRCHOICE = All Attributes
    -> NullAttributeMapper
NullAttributeMapper
    SOURCE_ATTR_VAL = "Missing (Selected Attributes Only)"
    NULL_TREATMENT = Null
    ATTRCHOICE = Selected Attributes
    ATTRLIST = HC53 HC56 HC57 HML19 HML20 HML32 HML33 HML35 HV104 HV105 HVIDX
    -> AttributeCreator
AttributeCreator
    ATTR_LIST = !_OUTNAME,@Value(_OUTFILETAG),!_OUTNAME_LABELLED,@Value(_OUTFILETAG)_Labelled,CHILDID,@Value(HHID)_@Value(HVIDX)
    -> SchemaMapper
    -> File1 (writer CSV_4)
    -> Sampler_3

Bookmark: Interpret attr names / values
Note: The SchemaMappper is used as a one-stop transformer to make a copy of all coded value attributes, named to give the actual question text and containing the interpreted value descriptions, e.g. cooking fuel = "electricity" rather than "1". / (It could equally do it into the original attributes). / Value mappings are recorded in an external csv table, which was generated from the original DCF dictionary files.
SchemaMapper
    CSV__SKIP_LINES = 1
    CSV__FIELD_NAMES_AFTER_HEADER = no
    CSV__SKIP_FOOTER = 0
    CSV__GROUP_BY_DATASET = yes
    IDXSOURCECOL = ""
    CSV__ALLOW_SPACES_IN_COLUMN_NAMES = yes
    IDXSOURCEATTR = fme_feature_type
    MATCH_ATTRS = SurveyIdColumnNameInData SurveyID ValueFieldIn Value
    MAP_ATTRS = """""" ValueDescFieldOut ValueDesc
    CSV__DUPLICATE_DELIMS = no
    CSV__SCHEMA = char,33,,char,8,,number,4,0,char,10,,char,4,,char,8,,char,7,,number,2,0,char,3,,char,4,,char,3,,number,6,0
    DATASET = \\129.67.26.176\map_data\DHS_Automation\DataExtraction\20150626_FullSiteScrape\SchemaMappingSupport\SchemaMapperValueSpecs_RH1-RH6-RHML_AllValues_Labelled_GenericCommonFieldNames.csv
    CSV__STRIP_QUOTES = yes
    CSV__IN_SEPARATOR = ,
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    IDXDESTATTR = fme_feature_type
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    CSV_SCAN_MAX_FEATURES = 1000
    FORMAT = CSV
    CSV__IN_FIELD_NAMES = YES
    TABLE = SchemaMapperValueSpecs_RH1-RH6-RHML_AllValues_Labelled_GenericCommonFieldNames
    ROW_ID_ATTR = _schemamapper_row_ids
    IDXDESTCOL = ""
    MAPPED -> SchemaMapper_2
    UNMAPPED -> SchemaMapper_Unmapped
SchemaMapper_2
    CSV__SKIP_LINES = 1
    CSV__FIELD_NAMES_AFTER_HEADER = no
    CSV__SKIP_FOOTER = 0
    CSV__GROUP_BY_DATASET = yes
    IDXSOURCECOL = ""
    CSV__ALLOW_SPACES_IN_COLUMN_NAMES = yes
    IDXSOURCEATTR = fme_feature_type
    MATCH_ATTRS = SurveyIdColumnNameInData SurveyID
    MAP_ATTRS = ValueFieldIn ValueFieldOut """"""
    CSV__DUPLICATE_DELIMS = no
    CSV__SCHEMA = char,33,,char,8,,number,4,0,char,10,,char,4,,char,8,,char,7,,number,2,0,char,3,,char,4,,char,3,,number,6,0
    DATASET = \\129.67.26.176\map_data\DHS_Automation\DataExtraction\20150626_FullSiteScrape\SchemaMappingSupport\SchemaMapperValueSpecs_RH1-RH6-RHML_AllValues_Labelled_GenericCommonFieldNames.csv
    CSV__STRIP_QUOTES = yes
    CSV__IN_SEPARATOR = ,
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    IDXDESTATTR = fme_feature_type
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__SCHEMA_WITH_COL_NAMES = Country,char,33,,Year,char,8,,Survey_ID_num,number,4,0,SurveyAPI_ID,char,10,,Type,char,4,,"Dataset range min",char,8,,"Dataset range max",char,7,,IgnoreDupe,number,2,0,DHS,char,3,,ISO3,char,4,,ISO2,char,3,,GAUL,number,6,0
    CSV_SCAN_MAX_FEATURES = 1000
    FORMAT = CSV
    CSV__IN_FIELD_NAMES = YES
    TABLE = SchemaMapperValueSpecs_RH1-RH6-RHML_AllValues_Labelled_GenericCommonFieldNames
    ROW_ID_ATTR = _schemamapper_row_ids
    IDXDESTCOL = ""
    MAPPED -> Sampler
    MAPPED -> FeatureMerger_2 [REQUESTOR]
SchemaMapper_Unmapped: Inspector

Bookmark: Generate output schema info for writer
Note: Because the schema mapper generates new attribs on the fly the workbench doesn't know their names so the writer for these needs to be dynamic. This requires instructions on what the output attrib names should be: generate one copy of this for each output file
Note: Get one per survey (not all surveys have all variables, so even though we're running all to a single file we need to sample one per survey then remove duplicates). Not one per outname as with single-file this wouldn't work.
Sampler
    GROUP_BY = SURVEY_ID_NUM
    RATE = 1
    SAMPLE_TYPE_LONG = First N Features
    SAMPLED -> BulkAttributeRenamer_2
Note: Add a prefix to survey id attribs
BulkAttributeRenamer_2
    PATTERN_ACTION_DISP = Add String Prefix
    REPLACE_STR = !_
    ATTRCHOICE = Selected Attributes
    ATTRLIST = ISO3 SURVEY_ID_NUM SURVEYID TYPE YEAR CHILDID
    -> AttributeExploder
Note: Convert to one feature per attribute
AttributeExploder
    ATTR_VALUE_LABEL = _attr_value
    EXPLODING_TYPE = Features
    KEEP_ATTRIBUTES = Yes
    ATTR_NAME_LABEL = name
    KEEP_GEOMETRY = No
    -> Tester_3
Note: Separate out survey id attribs from real data
Tester_3
    TEST_CLAUSE = TEST @Value(name) BEGINS_WITH !_
    TEST_MODE = Automatic
    TEST_DESCRIPTION = ""
    BOOL_OP = OR
    PASSED -> DuplicateRemover_2
    FAILED -> AttributeKeeper_5
DuplicateRemover_2
    KEYATTR = !_OUTNAME_LABELLED name
    UNIQUE -> AttributeKeeper_4
Note: Keep only the attribute exploder output, not the original attributes
AttributeKeeper_5
    KEEP_ATTRS = _attr_value,name,!_OUTNAME_LABELLED
    -> StringSearcher
Note: Fiind the original variable name, without the question text added by the schemamappers
StringSearcher
    MATCHED_RESULT_ATTR = _origName
    MATCHED_PARTS_ATTR = _blah
    CASE = no
    STRING_TO_SEARCH = @Value(name)
    REGEXP = ^\w+
    MATCHED -> Tester_5
Note: Drop the original (unrenamed) copies
Tester_5
    TEST_CLAUSE = TEST @Value(_origName) = @Value(name)
    TEST_MODE = Automatic
    TEST_DESCRIPTION = ""
    BOOL_OP = OR
    FAILED -> DuplicateRemover
Note: Keep only one copy of each attribute per output file (only one file in this version!)
DuplicateRemover
    KEYATTR = name !_OUTNAME_LABELLED
    UNIQUE -> FeatureMerger_3 [REQUESTOR]
Note: The second schemamapper creates an attribute for everything in the mapping, not just what's required / in the data. Use the attributes from before the schemamapper to select only the renamed attributes that should be kept (written to the output)
FeatureMerger_3
    JOIN_KEYS = @Value(_origName) @Value(_attr_name) AUTO @Value(!_OUTNAME_LABELLED) @Value(!_OUTNAME_LABELLED) AUTO
    MERGE_TYPE = Attributes Only
    ATTR_ACCUM_MODE = Merge Supplier
    ATTR_CONFLICT_RES = Use Requestor
    PROCESS_DUPS = No
    SUPPLIERS_FIRST = No
    IGNORE_NULLS = No
    MERGED -> AttributeKeeper_4
Note: Tidy up
AttributeKeeper_4
    KEEP_ATTRS = !_OUTNAME_LABELLED,name
    -> Sorter
Note: Sort, using the !_ prefix to ensure that the survey id attributes go before the data attributes.
Sorter
    SORT_PARM = !_OUTNAME_LABELLED ALPHA ASCENDING name ALPHA ASCENDING
    SORTED -> StringReplacer
Note: Get rid of the !_ prefix
StringReplacer
    NO_MATCH = _FME_NO_OP_
    CASE = no
    SRC_ATTRS = name
    REGEXP = yes
    FIND_TEXT = ^!_
    -> AttributeCreator_2
Note: set the data type for all attributes to be fme_buffer (equiv to text)
AttributeCreator_2
    ATTR_LIST = fme_data_type,fme_buffer
    -> Tester
Note: Don't keep the outname attribute as one to be written in itself
Tester
    TEST_CLAUSE:
      TEST @Value(name) BEGINS_WITH fme
      TEST @Value(name) BEGINS_WITH !_
      TEST @Value(name) CONTAINS OUTNAME
    TEST_MODE = Automatic
    TEST_DESCRIPTION = ""
    BOOL_OP = OR
    FAILED -> ListBuilder
Note: create the attribute{} list for the dynamic writer
ListBuilder
    LIST_NAME = attribute
    GRP_BY = !_OUTNAME_LABELLED
    -> FeatureMerger_2 [SUPPLIER]
