FME workspace GenerateSchemaMapping.fmw

Parameters:
- DestDataset_CSV = \\129.67.26.176\map_data\DHS_Automation\DataExtraction\20150626_FullSiteScrape\SchemaMappingSupport   # Destination CSV (CommaSeparatedValue) Folder
- SourceDataset_CSV_2 = \\129.67.26.176\map_data\DHS_Automation\DataExtraction\20150626_FullSiteScrape\SchemaMappingSupport\SchemaMapperValueSpecs_AllTables_NearlyAllSurveys_AllValues_Labelled_Wildcarded.csv   # Source CSV (CommaSeparatedValue) File(s)

Readers:
- CSV_3: CSV from $(SourceDataset_CSV_2)

Writers:
- CSV_2: CSV to $(DestDataset_CSV)

CSV (reader CSV_3)
    attributes: SurveyIdColumnNameInData char(9), SurveyID number(4,0), FileCode char(11), NameFieldColumnNameInData char(5), ValueFieldIn char(12), ValueFieldOut char(105), ValueDescFieldOut char(105), Value char(3), ValueDesc char(9), ValueType char(4)
    -> StringSearcher
StringSearcher
    CASE = no
    MATCHED_PARTS_ATTR = _matched_parts
    STRING_TO_SEARCH = @Value(ValueFieldIn)
    REGEXP = HV[0-2]|HML|HMH|^HC|ID
    MATCHED_RESULT_ATTR = _matched_characters
    MATCHED -> SchemaMapperValueSpecs_RH1-RH6-RHML_AllValues_Labelled (writer CSV_2)
SchemaMapperValueSpecs_RH1-RH6-RHML_AllValues_Labelled (writer CSV_2)
    attributes: SurveyIdColumnNameInData auto, SurveyID auto, FileCode auto, NameFieldColumnNameInData auto, ValueFieldIn auto, ValueFieldOut auto, ValueDescFieldOut auto, Value auto, ValueDesc auto, ValueType auto
